-- 
-- Output of registry data into file:
-- C:\Program Files (x86)\MiniEdit/Source.ASN
-- in format need to operate on the ASN source files.
-- 
-- Run on Mini-Edit Version 3.2.454 from ITSware.net DSRC tools
-- From file: SAE_J2735\FinalBuild\J2735_R41.its
-- Last Changed:  [Mod: 11/19/2014 00:00:00 AM]
-- This export was created on 11/19/2014  at 00:00:00 AM 
-- ###################################################
-- 
-- 
-- Run this file with a line like:
-- asn1 source.txt -errorfile errs.txt -noun
-- 
-- The local module consisting of DEs / DFs and MSGs
DSRC DEFINITIONS AUTOMATIC TAGS::= BEGIN 
 
-- -_-_-_-_-_-_-_-_-_-_-_-_-_-_-_-_-_-_-_-_-_-_-_-_-_-_-_-_
-- 
-- Start of entries from table Dialogs...
-- This table typically contains dialog and operational exchange entries.
-- -_-_-_-_-_-_-_-_-_-_-_-_-_-_-_-_-_-_-_-_-_-_-_-_-_-_-_-_
-- 
 
-- Table contains no entries.  
 
-- -_-_-_-_-_-_-_-_-_-_-_-_-_-_-_-_-_-_-_-_-_-_-_-_-_-_-_-_
-- 
-- Start of entries from table Messages...
-- This table typically contains message entries.
-- -_-_-_-_-_-_-_-_-_-_-_-_-_-_-_-_-_-_-_-_-_-_-_-_-_-_-_-_
-- 
 
 
-- MSG_BasicSafetyMessage  (BSM) (Desc Name) Record 1
BasicSafetyMessage ::=  SEQUENCE {
   -- Part I
   msgID       DSRCmsgID,                 -- 1 byte
   
   -- Sent as a single octet blob 
   blob1       BSMblob, 

   --   
   -- The blob consists of the following 38 packed bytes: 
   -- 
   -- msgCnt      MsgCount,             -x- 1 byte
   -- id          TemporaryID,          -x- 4 bytes
   -- secMark     DSecond,              -x- 2 bytes

   -- pos      PositionLocal3D,
     -- lat       Latitude,             -x- 4 bytes
     -- long      Longitude,            -x- 4 bytes
     -- elev      Elevation,            -x- 2 bytes
     -- accuracy  PositionalAccuracy,   -x- 4 bytes

   -- motion   Motion,
     -- speed     TransmissionAndSpeed, -x- 2 bytes
     -- heading   Heading,              -x- 2 byte
     -- angle     SteeringWheelAngle    -x- 1 bytes
     -- accelSet  AccelerationSet4Way,  -x- 7 bytes 
   
   -- control  Control,
   -- brakes      BrakeSystemStatus,    -x- 2 bytes
   
   -- basic    VehicleBasic,
   -- size        VehicleSize,          -x- 3 bytes
   
   -- Part II, sent as required 
   -- Part II, 
   safetyExt     VehicleSafetyExtension OPTIONAL, 
   status        VehicleStatus          OPTIONAL,  

   ... -- # LOCAL_CONTENT
   }
 
 
 
-- MSG_BasicSafetyMessage_Verbose  (VBSM) (Desc Name) Record 2
BasicSafetyMessageVerbose ::=  SEQUENCE {
   -- Part I, sent at all times 
   msgID       DSRCmsgID,            -- App ID value, 1 byte
   
   msgCnt      MsgCount,             -- 1 byte
   id          TemporaryID,          -- 4 bytes
   secMark     DSecond,              -- 2 bytes
   -- pos      PositionLocal3D,
   lat         Latitude,             -- 4 bytes 
   long        Longitude,            -- 4 bytes
   elev        Elevation,            -- 2 bytes
   accuracy    PositionalAccuracy,   -- 4 bytes
   
   -- motion   Motion,
   speed       TransmissionAndSpeed, -- 2 bytes
   heading     Heading,              -- 2 bytes
   angle       SteeringWheelAngle,   -- 1 bytes
   accelSet    AccelerationSet4Way,  -- 7 bytes
   
   -- control  Control,
   brakes      BrakeSystemStatus,    -- 2 bytes
   
   -- basic    VehicleBasic,
   size        VehicleSize,          -- 3 bytes
   
   -- Part II, sent as required 
   -- Part II, 
   safetyExt   VehicleSafetyExtension OPTIONAL, 
   status      VehicleStatus          OPTIONAL,  
   ... -- # LOCAL_CONTENT
   }
 
 
 
-- MSG_CommonSafetyRequest (CSR) (Desc Name) Record 3
CommonSafetyRequest ::=  SEQUENCE {
   msgID       DSRCmsgID,                 
   msgCnt      MsgCount OPTIONAL, 
   id          TemporaryID OPTIONAL,               
                                          
   -- Note: Uses the same request as probe management
   requests    SEQUENCE (SIZE(1..32)) OF RequestedItem,

   ... -- # LOCAL_CONTENT
   }
 
 
 
-- MSG_EmergencyVehicleAlert (EVA) (Desc Name) Record 4
EmergencyVehicleAlert ::=  SEQUENCE {
   msgID           DSRCmsgID,   
   id              TemporaryID OPTIONAL, 
   rsaMsg          RoadSideAlert, 
				-- the DSRCmsgID inside this 
                                -- data frame is set as per the 
                                -- RoadSideAlert.  The CRC is
                                -- set to a value of zero. 
   responseType    ResponseType                   OPTIONAL, 
   details         EmergencyDetails               OPTIONAL,   
                   -- Combines these 3 items: 
                   -- SirenInUse,                     
                   -- LightbarInUse,                  
                   -- MultiVehicleReponse,

   mass            VehicleMass                    OPTIONAL,
   basicType       VehicleType                    OPTIONAL,  
                                -- gross size and axle cnt
   
   -- type of vehicle and agency when known
   vehicleType     ITIS.VehicleGroupAffected      OPTIONAL,      
   responseEquip   ITIS.IncidentResponseEquipment OPTIONAL, 
   responderType   ITIS.ResponderGroupAffected    OPTIONAL,    
   crc             MsgCRC,
   ... -- # LOCAL_CONTENT
   }
 
 
 
-- MSG_IntersectionCollisionAvoidance  (ICA) (Desc Name) Record 5
IntersectionCollision ::=  SEQUENCE {
   msgID          DSRCmsgID,                 
   msgCnt         MsgCount,                 
   id             TemporaryID,               
   secMark        DSecond OPTIONAL,
   path           PathHistory, 
                  -- a set of recent path histories
   intersetionID  IntersectionID,      
                  -- the applicable Intersection, from the MAP-GID
                  -- the best applicable movement, from the MAP-GID
   laneNumber     LaneNumber,          
                  -- the best applicable Lane, from the MAP-SPAT-GID
                  -- zero sent if unknown
   eventFlag      EventFlags,
                  -- used to convey vehicle Panic Events,  
                  -- Set to indicate "Intersection Violation" 
   ... -- # LOCAL_CONTENT
   }
 
 
 
-- MSG_MapData  (MAP) (Desc Name) Record 6
MapData ::=  SEQUENCE {
   msgID             DSRCmsgID2,      
   msgSubID          DSRCmsgSubID OPTIONAL,  
   msgIssueRevision  MsgCount,        
   layerType         LayerType OPTIONAL,
   layerID           LayerID  OPTIONAL,
   intersections     IntersectionGeometryList OPTIONAL,
                     -- All Intersection definitions 
   
   -- NOTE:
   -- other map data will be added here as it is defined
   -- (curve warnings, construction routes, etc.)
   -- as an example of this:
   roadSegments      RoadSegmentList OPTIONAL,
                     -- All roadway descriptions
  
   dataParameters    DataParameters OPTIONAL,
                     -- Any meta data regarding the map contents
   
   restrictionList   RestrictionClassList OPTIONAL,
                     -- Any restriction ID tables which have  
                     -- established for these map entries 
   regional          RegionalMapData OPTIONAL, 
                     -- regional extensions
   crc               MsgCRC OPTIONAL,
                     -- The crc may be provided by other layers
                     -- and when encoding in UPER is not to be used 
   ... -- # LOCAL_CONTENT
   }
 
 
 
-- MSG_NMEA_Corrections  (NMEA) (Desc Name) Record 7
NMEA-Corrections ::=  SEQUENCE {
   msgID     DSRCmsgID,   
   rev       NMEA-Revision,
             -- the specific edition of the standard
             -- that is being sent, normally 2.0
   msg       NMEA-MsgType,
             -- the message and sub-message type, as
             -- defined in the revision being used
   -- NOTE as the message type is also in the payload, 
   wdCount   INTEGER (0..1023),
             -- a count of bytes to follow
   payload   NMEA-Payload, 
   ...
   }
 
 
 
-- MSG_ProbeDataManagement  (PDM) (Desc Name) Record 8
ProbeDataManagement ::=  SEQUENCE {
   msgID                DSRCmsgID,        -- This is a unique message 
                                          -- identifier, NOT related to 
                                          -- the PSID\PSC
   sample               Sample,           -- identifies vehicle  
                                          -- population affected
   directions           HeadingSlice,       
                                          -- Applicable headings/directions
   term CHOICE {                          
      termtime          TermTime,         -- Terminate management process 
                                          -- based on Time-to-Live
      termDistance      TermDistance      -- Terminate management process 
                                          -- based on Distance-to-Live
      },
   snapshot CHOICE {
      snapshotTime      SnapshotTime,     -- Collect snapshots based on time
      snapshotDistance  SnapshotDistance  -- Collect snapshots based on Distance
      },
   txInterval           TxTime,           -- Time Interval at which to send snapshots
   cntTthreshold        Count,            -- number of thresholds that will be changed
   dataElements SEQUENCE (SIZE(1..32)) OF 
                        VehicleStatusRequest,  
                                          -- a data frame and its assoc thresholds
   
   ...
   }
 
 
 
-- MSG_ProbeVehicleData  (PVD) (Desc Name) Record 9
ProbeVehicleData ::=  SEQUENCE {
   msgID           DSRCmsgID,            -- App ID value, 1 byte
   segNum          ProbeSegmentNumber OPTIONAL,   
                                         -- a short term Ident value
                                         -- not used when ident is used
   probeID         VehicleIdent OPTIONAL, 
                                         -- ident data for selected 
                                         -- types of vehicles    
   startVector     FullPositionVector,   -- the space and time of 
                                         -- transmission to the RSU
   vehicleType     VehicleType,          -- type of vehicle, 1 byte
   cntSnapshots    Count OPTIONAL,   
                                         -- a count of how many snaphots 
                                         -- type entries will follow
   snapshots       SEQUENCE (SIZE(1..32)) OF Snapshot,               
                                         -- a seq of name-value pairs 
                                         -- along with the space and time 
                                         -- of the first measurement set
   ... -- # LOCAL_CONTENT 
   } -- Est size about 64 bytes plus snapshot sizes (about 12 per)
 
 
 
-- MSG_RoadSideAlert  (RSA) (Desc Name) Record 10
RoadSideAlert ::=  SEQUENCE { 
   msgID         DSRCmsgID,                 
                 -- the message type. 
   msgCnt        MsgCount,   
   typeEvent     ITIS.ITIScodes,
                 -- a category and an item from that category 
                 -- all ITS stds use the same types here
                 -- to explain the type of  the 
                 -- alert / danger / hazard involved
                 -- two bytes in length
   description   SEQUENCE (SIZE(1..8)) OF ITIS.ITIScodes OPTIONAL,
                 -- up to eight ITIS code entries to further
                 -- describe the event, give advice, or any 
                 -- other ITIS codes
                 -- up to 16 bytes in length 
   priority      Priority OPTIONAL,  
                 -- the urgency of this message, a relative
                 -- degree of merit compared with other 
                 -- similar messages for this type (not other
                 -- message being sent by the device), nor a 
                 -- priority of display urgency
                 -- one byte in length
   heading       HeadingSlice  OPTIONAL,       
                 -- Applicable headings/direction
   extent        Extent OPTIONAL,  
                 -- the spatial distance over which this
                 -- message applies and should be presented 
                 -- to the driver
                 -- one byte in length
   positon       FullPositionVector OPTIONAL, 
                 -- a compact summary of the position,
                 -- heading, rate of speed, etc of the 
                 -- event in question. Including stationary
                 -- and wide area events. 
   furtherInfoID FurtherInfoID OPTIONAL,
                 -- a link to any other incident 
                 -- information data that may be available 
                 -- in the normal ATIS incident description 
                 -- or other messages
                 -- 1~2 bytes in length
    crc          MsgCRC
    }
 
 
 
-- MSG_RTCM_Corrections  (RTCM) (Desc Name) Record 11
RTCM-Corrections ::=  SEQUENCE {
   msgID     DSRCmsgID, 
   msgCnt    MsgCount, 
   rev       RTCM-Revision,
             -- the specific edition of the standard
             -- that is being sent

   anchorPoint FullPositionVector OPTIONAL,
   -- precise observer position, if needed

   -- precise ant position and noise data
   rtcmHeader  RTCMHeader,
   -- octets of:
   -- status      GPSstatus               
   -- antOffsets  AntennaOffsetSet(x,y,z)                      
   
   -- one or more RTCM messages
   rtcmSets    SEQUENCE (SIZE(1..5)) OF RTCMmsg,
   ... -- # LOCAL_CONTENT
   }
 
 
 
-- MSG_SignalRequestMessage  (SRM) (Desc Name) Record 12
SignalRequestMsg ::=  SEQUENCE {
   msgID           DSRCmsgID, 
   msgCnt          MsgCount,            

   -- Request Data 
   request        SignalRequest,
                  -- the specific request to the intersection
                  -- contains IntersectionID, cancel flags,
                  -- requested action, optional lanes data
   
   timeOfService  DTime  OPTIONAL,
                  -- the time in the near future when service is
                  -- requested to start
   
   endOfService   DTime  OPTIONAL,
                  -- the time in the near future when service is
                  -- requested to end

   transitStatus  TransitStatus OPTIONAL, 
                  -- additional information pertaining 
                  -- to transit events

   -- User Data
   vehicleVIN     VehicleIdent  OPTIONAL,
                  -- a set of unique strings to identify the requesting vehicle
   
   vehicleData    BSMblob,
                  -- current position data about the vehicle
   
   status         VehicleRequestStatus  OPTIONAL,
                  -- current status data about the vehicle
 
   ...
   }
 
 
 
-- MSG_SignalStatusMessage  (SSM) (Desc Name) Record 13
SignalStatusMessage ::=  SEQUENCE { 
   msgID         DSRCmsgID,   
   msgCnt        MsgCount, 
   id            IntersectionID,  
                 -- this provides a unique mapping to the  
                 -- intersection map in question 
                 -- which provides complete location  
                 -- and approach/move/lane data 
                 -- as well as zones for priority/preemption
   status        IntersectionStatusObject, 
                 -- general status of the signal controller
   priority      SEQUENCE (SIZE(1..7)) OF SignalState OPTIONAL, 
                 -- all active priority state data 
                 -- is found here 
   priorityCause VehicleIdent  OPTIONAL, 
                 -- vehicle that requested  
                 -- the current priority   
   prempt        SEQUENCE (SIZE(1..7)) OF SignalState OPTIONAL, 
                 -- all active preemption state data 
                 -- is found here 
   preemptCause  VehicleIdent  OPTIONAL, 
                 -- vehicle that requested  
                 -- the current preempt 
   transitStatus TransitStatus OPTIONAL, 
                 -- additional information pertaining 
                 -- to transit event, if that is the active event
   ...
   }
 
 
 
-- MSG_SignalPhaseAndTiming Message  (SPAT) (Desc Name) Record 14
SPAT ::=  SEQUENCE { 
   msgID         DSRCmsgID2,      
   msgSubID      DSRCmsgSubID OPTIONAL,  
   name          DescriptiveName OPTIONAL, 
                 -- human readable name for this collection 
                 -- to be used only in debug mode
   
   intersections IntersectionStateList,
                 -- sets of SPAT data (one per intersection)  
   
   -- If PrioritizationResponse data is required, it is found 
   -- in the RegionalSPAT entry below
   
   regional     RegionalSPAT OPTIONAL, -- regional extensions
   ... -- # LOCAL_CONTENT
   }
 
 
 
-- MSG_TravelerInformation Message  (TIM) (Desc Name) Record 15
TravelerInformation ::=  SEQUENCE {
   msgID           DSRCmsgID, 
   packetID        UniqueMSGID    OPTIONAL,    
   urlB            URL-Base       OPTIONAL,  
   dataFrameCount  Count          OPTIONAL, 
   
   dataFrames SEQUENCE (SIZE(1..8)) OF SEQUENCE {
   
      -- Part I, Frame header
      frameType   TravelerInfoType,  -- (enum, advisory or road sign)
      msgId       CHOICE  {
                     furtherInfoID   FurtherInfoID,
                                     -- links to ATIS msg
                     roadSignID      RoadSignID  
                                     -- an ID to other data
                     },
      startYear   DYear OPTIONAL, 
                  -- Current year used if missing
      startTime   MinuteOfTheYear,
      duratonTime MinutesDuration,
      priority    SignPrority,
  
      -- Part II, Applicable Regions of Use
     commonAnchor         Position3D     OPTIONAL, 
                          -- a shared anchorpoint 
     commonLaneWidth      LaneWidth      OPTIONAL,   
                          -- a shared lane width 
     commonDirectionality DirectionOfUse OPTIONAL, 
                          -- a shared direction of use
     regions  SEQUENCE (SIZE(1..16)) OF ValidRegion,
   
      -- Part III, Content
      content  CHOICE  {
                  advisory       ITIS.ITIScodesAndText,           
                                 -- typical ITIS warnings
                  workZone       WorkZone,       
                                 -- work zone signs and directions
                  genericSign    GenericSignage, 
                                 -- MUTCD signs and directions
                  speedLimit     SpeedLimit,     
                                 -- speed limits and cautions
                  exitService    ExitService     
                                 -- roadside avaiable services
                  -- other types may be added in future revisions
                  },  --# UNTAGGED 
      url     URL-Short OPTIONAL  -- May link to image or other content
      },
   crc        MsgCRC,
   ... -- # LOCAL_CONTENT
   }
 
 
 
-- MSG_UPER_Frame_USA (UPER) CHANGED (Desc Name) Record 16
UPERframe ::=  SEQUENCE {
   msgID          DSRCmsgID2,      
                  -- id of this message 
   msgSubID       DSRCmsgSubID OPTIONAL,      
                  -- sub id of this message 
   timeStamp      MinuteOfTheYear OPTIONAL,
   contentID      DSRCmsgID2,      
                  -- id of message to follow
   msgBlob        UPER-Blob, 
                  -- encoded message in UPER form
                  -- rounded the next full DER byte

   ..., -- # LOCAL_CONTENT
   crc            MsgCRC   OPTIONAL 
                  -- The crc may be provided by other layers
   }
 
 
-- -_-_-_-_-_-_-_-_-_-_-_-_-_-_-_-_-_-_-_-_-_-_-_-_-_-_-_-_
-- 
-- Start of entries from table Data_Frames...
-- This table typically contains data frame entries.
-- -_-_-_-_-_-_-_-_-_-_-_-_-_-_-_-_-_-_-_-_-_-_-_-_-_-_-_-_
-- 
 
 
-- DF_AccelerationSet4Way (Desc Name) Record 1
AccelerationSet4Way ::= OCTET STRING (SIZE(7)) 
   -- composed of the following:
   -- SEQUENCE {
   --    long Acceleration,          -x- Along the Vehicle Longitudinal axis
   --    lat  Acceleration,          -x- Along the Vehicle Lateral axis
   --    vert VerticalAcceleration,  -x- Along the Vehicle Vertical axis
   --    yaw  YawRate
   --    }
 
 
 
-- DF_AccelSteerYawRateConfidence (Desc Name) Record 2
AccelSteerYawRateConfidence ::=  SEQUENCE {
   yawRate             YawRateConfidence, 
                       -- 3 bits
   acceleration        AccelerationConfidence, 
                       -- 3 bits
   steeringWheelAngle  SteeringWheelAngleConfidence 
                       -- 2 bits
   }
 
 
 
-- DF_AdvisorySpeed (Desc Name) Record 3
AdvisorySpeed ::=  SEQUENCE {
   type        AdvisorySpeedType,
               -- the type of advisory which this is.
   speed       SpeedAdvice OPTIONAL,
               -- See Remarks under the SpeedAdvice entry for
               -- converting and transmitting a speed expressed
               -- in MPH to units of 0.1 m/s
               -- This element is optional ONLY when superceded 
               -- by the presence of a regional speed element found in
               -- RegionalAdvisorySpeed
   confidence  SpeedConfidence OPTIONAL,
               -- A confidence value for the above speed
   distance    ZoneLength OPTIONAL,
               -- Unit = 1 meter,  
               -- The distance indicates the region for which the advised speed 
               -- is recommended, it is specified upstream from the stop bar  
               -- along the connected egressing lane
   class       RestrictionClassID OPTIONAL,
               -- the vehicle types to which it applies
               -- when absent, the AdvisorySpeed applies to
               -- all motor vehicle types
   regional    RegionalAdvisorySpeed OPTIONAL,
               -- regional extensions
   ...
   }
 
 
 
-- DF_AdvisorySpeedList (Desc Name) Record 4
AdvisorySpeedList ::=  SEQUENCE (SIZE(1..16)) OF AdvisorySpeed
 
 
 
-- DF_AntennaOffsetSet (Desc Name) Record 5
AntennaOffsetSet ::= OCTET STRING (SIZE(4)) 
   -- defined as:
   -- SEQUENCE {
   -- antOffsetX  INTEGER (-8191..8191), 
                  -- 14 bits in length
                  -- units of 1cm from center
                  -- 8191 to be used for unavailable 
   -- antOffsetY  INTEGER (-255..255),     
                  -- 9 bits in length
                  -- units of 1cm from center
                  -- 255 to be used for unavailable 
   -- antOffsetZ  INTEGER (0..511)        
                  -- 9 bits in length
                  -- units of 1cm from ground
                  -- 511 to be used for unavailable 
   -- }
 
 
 
-- DF_BrakeSystemStatus (Desc Name) Record 6
BrakeSystemStatus ::= OCTET STRING (SIZE(2))
   -- Encoded with the packed content of: 
   -- SEQUENCE {
   --   wheelBrakes        BrakeAppliedStatus,
   --                      -x- 4 bits
   --   wheelBrakesUnavailable  BOOL
   --                      -x- 1 bit (1=true)
   --   spareBit
   --                      -x- 1 bit, set to zero
   --   traction           TractionControlState,
   --                      -x- 2 bits
   --   abs                AntiLockBrakeStatus, 
   --                      -x- 2 bits
   --   scs                StabilityControlStatus,
   --                      -x- 2 bits
   --   brakeBoost         BrakeBoostApplied, 
   --                      -x- 2 bits
   --   auxBrakes          AuxiliaryBrakeStatus,
   --                      -x- 2 bits
   --   }
 
 
 
-- DF_BSM_Blob (Desc Name) Record 7
BSMblob ::= OCTET STRING (SIZE(38)) 
   -- made up of the following 38 packed bytes:
   -- msgCnt      MsgCount,             -x- 1 byte
   -- id          TemporaryID,          -x- 4 bytes
   -- secMark     DSecond,              -x- 2 bytes

   -- lat         Latitude,             -x- 4 bytes 
   -- long        Longitude,            -x- 4 bytes
   -- elev        Elevation,            -x- 2 bytes
   -- accuracy    PositionalAccuracy,   -x- 4 bytes
   
   -- speed       TransmissionAndSpeed, -x- 2 bytes
   -- heading     Heading,              -x- 2 byte
   -- angle       SteeringWheelAngle    -x- 1 byte
   -- accelSet    AccelerationSet4Way,  -x- accel set (four way) 7 bytes
  
   -- brakes      BrakeSystemStatus,    -x- 2 bytes
   -- size        VehicleSize,          -x- 3 bytes
 
 
 
-- DF_BumperHeights (Desc Name) Record 8
BumperHeights ::=  SEQUENCE {
   frnt       BumperHeightFront, 
   rear       BumperHeightRear
   }
 
 
 
-- DF_Circle (Desc Name) Record 9
Circle ::=  SEQUENCE {
   center   Position3D,
   raduis   CHOICE {
               radiusSteps  INTEGER (0..32767), 
                              -- in unsigned values where 
                              -- the LSB is in units of 2.5 cm
               miles        INTEGER (1..2000),
               km           INTEGER (1..5000)
            } --# UNTAGGED
   }
 
 
 
-- DF_ComputedLane (Desc Name) Record 10
ComputedLane ::=  SEQUENCE {
   -- Data needed to created a computed lane
   referenceLaneId    LaneID,
                         -- the lane ID upon which this 
                         -- computed lane will be based 
   -- Lane Offset in X and Y direction
   offsetXaxis        CHOICE {
                         small   DrivenLineOffsetSm, 
                         large   DrivenLineOffsetLg
                         },  
   offsetYaxis        CHOICE {
                         small   DrivenLineOffsetSm, 
                         large   DrivenLineOffsetLg
                         },  
                         -- An path X offset value for translations of the 
                         -- path's points when created translated lanes. 
                         -- The values found in the reference lane are 
                         -- all offset based on the X and Y values from 
                         -- the coordinates of the reference lane's 
                         -- starting initial point.   
   -- Lane Rotation
   rotateXY           Angle OPTIONAL, 
                         -- A path rotation value for the entire lane
                         -- Observe that this rotates the existing orientation 
                         -- of the referenced lane, it does not replace it.
   -- Lane Path Scale (zooming)
   scaleXaxis         Scale-B12 OPTIONAL, 
   scaleYaxis         Scale-B12 OPTIONAL, 
                         -- value for translations or zooming of the path's 
                         -- points. The values found in the reference lane 
                         -- are all expanded of contracted based on the X 
                         -- and Y and width values from the coordinates of 
                         -- the reference lane's starting initial point.  
                         -- The Z axis remains untouched.  
   regional           RegionalComputedLane OPTIONAL, 
                      -- regional extensions
   ... 
   }
 
 
 
-- DF_ConfidenceSet (Desc Name) Record 11
ConfidenceSet ::=  SEQUENCE {
   accelConfidence      AccelSteerYawRateConfidence OPTIONAL,    
   speedConfidence      SpeedandHeadingandThrottleConfidence OPTIONAL,      
   timeConfidence       TimeConfidence OPTIONAL,           
   posConfidence        PositionConfidenceSet OPTIONAL,           
   steerConfidence      SteeringWheelAngleConfidence OPTIONAL,
   throttleConfidence   ThrottleConfidence OPTIONAL,
   ... -- # LOCAL_CONTENT
   }
 
 
 
-- DF_ConnectingLane (Desc Name) Record 12
ConnectingLane ::=  SEQUENCE {
   lane      LaneID,   -- Index of the connecting lane
   maneuver  AllowedManeuvers OPTIONAL
                       -- The Maneuver between 
                       -- the enclosing lane and this lane
                       -- at the stop line to connect them
   }
 
 
 
-- DF_Connection (Desc Name) Record 13
Connection ::=  SEQUENCE {
   -- The subject lane connecting to this lane is:
   connectingLane     ConnectingLane, 
                      -- The index of the connecting lane and also
                      -- the maneuver from the current lane to it
   remoteIntersection IntersectionReferenceID OPTIONAL,  
                      -- This entry is only used when the 
                      -- indicated connecting lane belongs 
                      -- to another intersection layout. This 
                      -- provides a means to create meshes of lanes
   
   -- SPAT mapping details at the stop line are:
   signalGroup        SignalGroupID OPTIONAL,    
                      -- The matching signal group send by 
                      -- the SPAT message for this lane/maneuver
                      -- Shall be present unless the connectingLane 
                      -- has not signal group (is un-signalized)
   userClass          RestrictionClassID OPTIONAL, 
                      -- The Restriction Class of users this applies to
                      -- The use of some lane/maneuver and SignalGroupID 
                      -- pairings are restricted to selected users
                      -- when absent, the SignalGroupID applies to all
   
   -- Movement assist details are given by:
   connectionID       LaneConnectionID OPTIONAL
                      -- An optional connection index used to 
                      -- relate this lane connection to any dynamic 
                      -- clearance data in the SPAT. Note that
                      -- the index may be shared with other 
                      -- connections if the clearance data is common
   }
 
 
 
-- DF_ConnectionManeuverAssist (Desc Name) Record 14
ConnectionManeuverAssist ::=  SEQUENCE {
   connectionID         LaneConnectionID,
                        -- the common connectionID used by all lanes to which
                        -- this data applies 
                        -- (this value traces to ConnectsTo entries in lanes)
   -- Expected Clearance Information
   queueLength          ZoneLength OPTIONAL,
                        -- Unit = 1 meter, 0 = no queue
                        -- The distance from the stop line to the back 
                        -- edge of the last vehicle in the queue,                     
                        -- as measured along the lane center line.
   availableStorageLength ZoneLength OPTIONAL,
                        -- Unit = 1 meter, 0 = no space remains
                        -- Distance (e.g. beginning from the downstream 
                        -- stop-line up to a given distance) with a high 
                        -- probability for successfully executing the 
                        -- connection maneuver between the two lanes 
                        -- during the current cycle. 
                        -- Used for enhancing the awareness of vehicles 
                        -- to anticipate if they can pass the stop line
                        -- of the lane. Used for optimizing the green wave, 
                        -- due to knowledge of vehicles waiting in front 
                        -- of a red light (downstream).
                        -- The element nextTime in TimeChangeDetails
                        -- in the containing data frame contains the next 
                        -- timemark at which an active phase is expected, 
                        -- a form of storage flush interval.
   waitOnStop           WaitOnStopline OPTIONAL,
                        -- If "true", the vehicles on this specific connecting 
                        -- maneuver have to stop on the stop-line and not 
                        -- to enter the collision area 
   pedBicycleDetect     PedestrianBicycleDetect OPTIONAL,
                        -- true if ANY ped or bicycles are detected crossing 
                        -- the above lanes. Set to false ONLY if there is a 
                        -- high certainty that there are none present, 
                        -- otherwise element is not sent.
   regional             RegionalConnectionManeuverAssist OPTIONAL, 
                        -- regional extensions
   ... -- # LOCAL_CONTENT
   }
 
 
 
-- DF_ConnectsToList (Desc Name) Record 15
ConnectsToList ::=  SEQUENCE (SIZE(1..16)) OF Connection
 
 
 
-- DF_DataParameters (Desc Name) Record 16
DataParameters ::=  SEQUENCE {
   processMethod     IA5String(SIZE(1..255)) OPTIONAL, 
   processAgency     IA5String(SIZE(1..255)) OPTIONAL, 
   lastCheckedDate   IA5String(SIZE(1..255)) OPTIONAL, 
   geoidUsed         IA5String(SIZE(1..255)) OPTIONAL, 
   ... -- # LOCAL_CONTENT
   }
 
 
 
-- DF_DDate (Desc Name) Record 17
DDate ::=  SEQUENCE {
   year    DYear,            -- 2 bytes
   month   DMonth,           -- 1 byte
   day     DDay              -- 1 byte
   }
 
 
 
-- DF_DDateTime (Desc Name) Record 18
DDateTime ::=  SEQUENCE {
   year    DYear    OPTIONAL,    -- 2 bytes
   month   DMonth   OPTIONAL,    -- 1 byte
   day     DDay     OPTIONAL,    -- 1 byte
   hour    DHour    OPTIONAL,    -- 1 byte
   minute  DMinute  OPTIONAL,    -- 1 byte
   second  DSecond  OPTIONAL     -- 2 bytes
   }
 
 
 
-- DF_DFullTime (Desc Name) Record 19
DFullTime ::=  SEQUENCE {
   year    DYear,            -- 2 bytes
   month   DMonth,           -- 1 byte
   day     DDay,             -- 1 byte
   hour    DHour,            -- 1 byte
   minute  DMinute           -- 1 byte
   }
 
 
 
-- DF_DMonthDay (Desc Name) Record 20
DMonthDay ::=  SEQUENCE {
   month   DMonth,           -- 1 byte
   day     DDay              -- 1 byte
   }
 
 
 
-- DF_DTime (Desc Name) Record 21
DTime ::=  SEQUENCE {
   hour    DHour,            -- 1 byte
   minute  DMinute,          -- 1 byte
   second  DSecond           -- 2 bytes
   }
 
 
 
-- DF_DYearMonth (Desc Name) Record 22
DYearMonth ::=  SEQUENCE {
   year    DYear,            -- 2 bytes
   month   DMonth            -- 1 byte
   }
 
 
 
-- DF_EnabledLaneList (Desc Name) Record 23
EnabledLaneList ::=  SEQUENCE (SIZE(1..16)) OF LaneID
   -- The unique ID numbers for each
   -- lane object which is 'active' 
   -- as part of the dynamic map contents.
 
 
 
-- DF_ITIS_Phrase_ExitService (Desc Name) Record 24
ExitService ::=  SEQUENCE (SIZE(1..10)) OF SEQUENCE {
  item-es CHOICE    {
       itis   ITIS.ITIScodes,
       text   IA5String  (SIZE(1..16))
       } -- # UNTAGGED
  }
 
 
 
-- DF_FullPositionVector (Desc Name) Record 25
FullPositionVector ::=  SEQUENCE {
   utcTime             DDateTime OPTIONAL,   -- time with mSec precision
   long                Longitude,            -- 1/10th microdegree
   lat                 Latitude,             -- 1/10th microdegree
   elevation           Elevation OPTIONAL,   -- 3 bytes, 0.1 m
   heading             Heading OPTIONAL, 
   speed               TransmissionAndSpeed OPTIONAL,
   posAccuracy         PositionalAccuracy OPTIONAL,
   timeConfidence      TimeConfidence OPTIONAL,
   posConfidence       PositionConfidenceSet OPTIONAL,
   speedConfidence     SpeedandHeadingandThrottleConfidence OPTIONAL, 
   ... -- # LOCAL_CONTENT 
   }
 
 
 
-- DF_GenericLane (Desc Name) Record 26
GenericLane ::=  SEQUENCE { 
   laneID           LaneID, 
                    -- The unique ID number assigned 
                    -- to this lane object
   name             DescriptiveName OPTIONAL,        
                    -- often for debug use only 
                    -- but at times used to name ped crossings
   ingressApproach  ApproachID OPTIONAL, -- inbound
   egressApproach   ApproachID OPTIONAL, -- outbound
                    -- Approach IDs to which this lane belongs
   laneAttributes   LaneAttributes, 
                    -- All Attribute information about 
                    -- the basic selected lane type
                    -- Directions of use, Geometric co-sharing
                    -- and Type Specific Attributes
                    -- These Attributes are 'lane - global' that is,
                    -- they are true for the entire length of the lane
   maneuvers        AllowedManeuvers OPTIONAL,
                    -- the permitted maneuvers for this lane
   nodeList         NodeList2,
                    -- Lane spatial path information as well as
                    -- various Attribute information along the node path  
                    -- Attributes found here are more general and may
                    -- come and go over the length of the lane.
   connectsTo       ConnectsToList OPTIONAL, 
                    -- a list of other lanes and their signal group IDs
                    -- each connecting lane and its signal group ID
                    -- is given, therefore this element provides the
                    -- information formally in "signalGroups" in prior
                    -- editions.
   overlays         OverlayLaneList OPTIONAL, 
                    -- A list of any lanes which have spatial paths that
                    -- overlay (run on top of, and not simply cross) 
                    -- the path of this lane when used
   regional         RegionalGenericLane OPTIONAL, 
                    -- regional extensions
   ... 
   }
 
 
 
-- DF_ITIS_Phrase_GenericSignage (Desc Name) Record 27
GenericSignage ::=  SEQUENCE (SIZE(1..10)) OF SEQUENCE {
  item-gs CHOICE    {
       itis   ITIS.ITIScodes,
       text   IA5String  (SIZE(1..16))
       } -- # UNTAGGED
  }
 
 
 
-- DF_IntersectionGeometry (Desc Name) Record 28
IntersectionGeometry ::=  SEQUENCE {
   name        DescriptiveName OPTIONAL, 
                            -- For debug use only
   id          IntersectionReferenceID,  
                            -- A globally unique value set, 
                            -- consisting of a regionID and 
                            -- intersection ID assignment
   revision    MsgCount,    

   -- Required default values about lane descriptions follow
   refPoint    Position3D-2, -- The reference from which subsequent 
                            -- data points are offset until a new
                            -- point is used. 
   laneWidth   LaneWidth OPTIONAL,   
                            -- Reference width used by all subsequent 
                            -- lanes unless a new width is given  
   speedLimits SpeedLimitList OPTIONAL, 
                            -- Reference regulatory speed limits
                            -- used by all subsequent 
                            -- lanes unless a new speed is given 
                            -- See Remarks under the SpeedAdvice entry 
                            -- for converting and transmitting a speed 
                            -- expressed in MPH to units of 0.1 m/s

   -- Complete details regarding each lane type in this intersection
   laneSet     LaneList,    -- Data about one or more lanes
                            -- (all lane data is found here)
   
   -- Data describing how to use and request preemption and
   -- priority services from this intersection (if supported)
   -- NOTE Additonal data may be added in the next release of the 
   -- standard at this point to handle this concept
   preemptPriorityData PreemptPriorityList OPTIONAL, 
                           -- data about one or more regional
                           -- preempt or priority zones 
   
   regional    RegionalIntersection  OPTIONAL,
               -- regional message content to be placed here
   ... 
   }
 
 
 
-- DF_IntersectionGeometryList (Desc Name) Record 29
IntersectionGeometryList ::=  SEQUENCE (SIZE(1..32)) OF IntersectionGeometry
 
 
 
-- DF_IntersectionReferenceID (Desc Name) Record 30
IntersectionReferenceID ::=  SEQUENCE {
   region  RoadRegulatorID OPTIONAL,
           -- a globally unique regional assignment value
           -- typical assigned to a regional DOT authority
           -- the value zero shall be used for testing needs
   id      IntersectionID
           -- a unique mapping to the intersection
           -- in question within the above region of use
   }
 
 
 
-- DF_IntersectionState (Desc Name) Record 31
IntersectionState ::=  SEQUENCE {
   name         DescriptiveName OPTIONAL, 
                -- human readable name for intersection  
                -- to be used only in debug mode
   id           IntersectionReferenceID,  
                -- A globally unique value set, consisting of a 
                -- regionID and intersection ID assignment
                -- provides a unique mapping to the 
                -- intersection MAP in question
                -- which provides complete location 
                -- and approach/move/lane data
   revision     MsgCount,    
   status       IntersectionStatusObject,
                -- general status of the controller(s)
   moy          MinuteOfTheYear OPTIONAL,
                -- Minute of current UTC year
                -- used only with messages to be archived 
   timeStamp    DSecond2 OPTIONAL, 
                -- the mSec point in the current UTC minute that
                -- this message was constructed
   enabledLanes EnabledLaneList OPTIONAL,  
                -- a list of lanes where the RevocableLane bit 
                -- has been set which are now active and 
                -- therefore part of the current intersection
   states       MovementList,
                -- Each Movement is given in turn
                -- and contains its signal phase state, 
                -- mapping to the lanes it applies to, and
                -- point in time it will end, and it
                -- may contain both active and future states 
   maneuverAssistList  ManeuverAssistList OPTIONAL,
                -- Assist data
   priority     SignalControlState OPTIONAL,
                -- the active priority state data, if present
   preempt      SignalControlState OPTIONAL,
                -- the active preemption state data, if present
   
   regional     RegionalIntersectionState OPTIONAL, 
                -- regional extensions   
   ... 
   }
 
 
 
-- DF_IntersectionStateList (Desc Name) Record 32
IntersectionStateList ::=  SEQUENCE (SIZE(1..32)) OF  IntersectionState
 
 
 
-- DF_J1939-Data Items (Desc Name) Record 33
J1939data ::=  SEQUENCE {
   -- Tire conditions 
   tires SEQUENCE (SIZE(0..16)) OF SEQUENCE {
      location              TireLocation              OPTIONAL, 
      pressure              TirePressure              OPTIONAL, 
      temp                  TireTemp                  OPTIONAL, 
      wheelSensorStatus     WheelSensorStatus         OPTIONAL, 
      wheelEndElectFault    WheelEndElectFault        OPTIONAL, 
      leakageRate           TireLeakageRate           OPTIONAL, 
      detection             TirePressureThresholdDetection OPTIONAL, 
      ...
      } OPTIONAL,      
   -- Vehicle Weight by axle
   axle SEQUENCE (SIZE(0..16)) OF SEQUENCE {
      location              AxleLocation              OPTIONAL, 
      weight                AxleWeight                OPTIONAL, 
      ...
      } OPTIONAL,      
   trailerWeight            TrailerWeight             OPTIONAL,     
   cargoWeight              CargoWeight               OPTIONAL, 
   steeringAxleTemperature  SteeringAxleTemperature   OPTIONAL, 
   driveAxleLocation        DriveAxleLocation         OPTIONAL, 
   driveAxleLiftAirPressure DriveAxleLiftAirPressure  OPTIONAL, 
   driveAxleTemperature     DriveAxleTemperature      OPTIONAL, 
   driveAxleLubePressure    DriveAxleLubePressure     OPTIONAL, 
   steeringAxleLubePressure SteeringAxleLubePressure  OPTIONAL, 
   ...
   }
 
 
 
-- DF_LaneAttributes (Desc Name) Record 34
LaneAttributes ::=  SEQUENCE {
   directionalUse  LaneDirection,      -- directions of lane use
   sharedWith      LaneSharing,        -- co-users of the lane path
   laneType        LaneTypeAttributes, -- specific lane type data
   regional        RegionalLaneAttributes OPTIONAL 
                                       -- regional extensions
   }
 
 
 
-- DF_LaneDataAttribute (Desc Name) Record 35
LaneDataAttribute ::=  CHOICE {
    -- Segment attribute types and the data needed for each
    pathEndPointAngle        DeltaAngle,  
                             -- adjusts final point/width slant
                             -- of the lane to align with the stop line
    laneCrownPointCenter     RoadwayCrownAngle,  
                             -- sets the canter of the road bed      
                             -- from centerline point
    laneCrownPointLeft       RoadwayCrownAngle,  
                             -- sets the canter of the road bed
                             -- from left edge
    laneCrownPointRight      RoadwayCrownAngle,  
                             -- sets the canter of the road bed
                             -- from right edge
    laneAngle                MergeDivergeNodeAngle,  
                             -- the angle or direction of another lane
                             -- this is required to support Japan style
                             -- when a merge point angle is required
    speedLimits              SpeedLimitList,
                             -- Reference regulatory speed limits
                             -- used by all segments
   
    -- Add others as needed, here or in regional space
    regional                 RegionalLaneDataAttribute,
                             -- regional extensions
    ...
    }
 
 
 
-- DF_LaneDataAttributeList (Desc Name) Record 36
LaneDataAttributeList ::=  SEQUENCE (SIZE(1..8)) OF LaneDataAttribute
 
 
 
-- DF_LaneList (Desc Name) Record 37
LaneList ::=  SEQUENCE (SIZE(1..255)) OF GenericLane
 
 
 
-- DF_LaneTypeAttributes (Desc Name) Record 38
LaneTypeAttributes ::=  CHOICE {
   vehicle        LaneAttributes-Vehicle,        -- motor vehicle lanes
   crosswalk      LaneAttributes-Crosswalk,      -- pedestrian crosswalks
   bikeLane       LaneAttributes-Bike,           -- bike lanes
   sidewalk       LaneAttributes-Sidewalk,       -- pedestrian sidewalk paths
   median         LaneAttributes-Barrier,        -- medians & channelization
   striping       LaneAttributes-Striping,       -- roadway markings
   trackedVehicle LaneAttributes-TrackedVehicle, -- trains and trolleys
   parking        LaneAttributes-Parking,        -- parking and stopping lanes
   ...
   }
 
 
 
-- DF_ManeuverAssistList (Desc Name) Record 39
ManeuverAssistList ::=  SEQUENCE (SIZE(1..16)) OF ConnectionManeuverAssist
 
 
 
-- DF_MovementEvent (Desc Name) Record 40
MovementEvent ::=  SEQUENCE {
   eventState   MovementPhaseState,
                -- Consisting of:
                -- Phase state (the basic 11 states)
                -- Directional, protected, or permissive state
   
   timing       TimeChangeDetails OPTIONAL,
                -- Timing Data in UTC time stamps for event
                -- includes start and min/max end times of phase
                -- confidence and estimated next occurrence
   
   speeds       AdvisorySpeedList OPTIONAL,
                -- various speed advisories for use by
                -- general and specific types of vehicles
                -- supporting green-wave and other flow needs
                -- See Remarks under the SpeedAdvice entry for
                -- converting and transmitting a speed expressed
                -- in MPH to units of 0.1 m/s
   
   regional     RegionalMovementEvent OPTIONAL, 
                -- regional extensions
   ... -- # LOCAL_CONTENT
   }
 
 
 
-- DF_MovementEventList (Desc Name) Record 41
MovementEventList ::=  SEQUENCE (SIZE(1..16)) OF MovementEvent
 
 
 
-- DF_MovementList (Desc Name) Record 42
MovementList ::=  SEQUENCE (SIZE(1..255)) OF MovementState
 
 
 
-- DF_MovementState (Desc Name) Record 43
MovementState ::=  SEQUENCE {
   movementName       DescriptiveName OPTIONAL,
                      -- uniquely defines movement by name   
                      -- human readable name for intersection  
                      -- to be used only in debug mode
   signalGroup        SignalGroupID,    
                      -- the group id is used to map to lists 
                      -- of lanes (and their descriptions) 
                      -- which this MovementState data applies to 
                      -- see comments in the Remarks for usage details 
   state-time-speed   MovementEventList,   
                      -- Consisting of sets of movement data with:
                      -- a)  SignalPhaseState
                      -- b)  TimeChangeDetails,  and 
                      -- c)  AdvisorySpeeds      (optional )
                      -- Note one or more of the movement events may be for 
                      -- a future time and that this allows conveying multiple 
                      -- predictive phase and movement timing for various uses
                      -- for the current signal group
   maneuverAssistList ManeuverAssistList OPTIONAL,
                      -- This information may also be placed in the 
                      -- IntersectionState when common information applies to
                      -- different lanes in the same way
   regional           RegionalMovementState OPTIONAL, 
                      -- regional extensions
   ... -- # LOCAL_CONTENT
   }
 
 
 
-- DF_Node (Desc Name) Record 44
Node ::=  SEQUENCE {
   delta       NodeOffsetPoint,
               -- A choice of which X,Y offset value to use  
               -- this includes various delta values as well a regional choices
   attributes  NodeAttributeSet OPTIONAL,
               -- Any optional Attributes which are needed
               -- This includes changes to the current lane width and elevation
   ... 
   }
 
 
 
-- DF_NodeAttributeList (Desc Name) Record 45
NodeAttributeList ::=  SEQUENCE (SIZE(1..8)) OF NodeAttribute
 
 
 
-- DF_NodeAttributeSet (Desc Name) Record 46
NodeAttributeSet ::=  SEQUENCE {
   localNode    NodeAttributeList OPTIONAL,
                -- Attribute states which pertain to this node point
   disabled     SegmentAttributeList OPTIONAL,
                -- Attribute states which are disabled at this node point
   enabled      SegmentAttributeList OPTIONAL,
                -- Attribute states which are enabled at this node point
                -- and which remain enabled until disabled or the lane ends
   data         LaneDataAttributeList OPTIONAL,
                -- Attributes which require an additional data values
                -- some of these are local to the node point, while others
                -- persist with the provided values until changed
                -- and this is indicated in each entry
   regional     RegionalNodeAttributeList OPTIONAL, 
                -- Regional extensions
   dWidth       Offset-B10 OPTIONAL,
                -- A value added to the current lane width
                -- at this node and from this node onwards, in 1cm steps
                -- lane width between nodes are a linear taper between pts
                -- the value of zero shall not be sent here
   dElevation   Offset-B10 OPTIONAL,
                -- A value added to the current Elevation 
                -- at this node from this node onwards, in 10cm steps
                -- elevations between nodes are a linear taper between pts
                -- the value of zero shall not be sent here
   ...
   }
 
 
 
-- DF_NodeList (Desc Name) Record 47
NodeList ::=  SEQUENCE (SIZE(1..64)) OF Offsets
   -- the Position3D ref point (starting point or anchor)
   -- is found in the outer object. 
   -- Offsets are additive from the last point.
 
 
 
-- DF_NodeList2 (Desc Name) Record 48
NodeList2 ::=  CHOICE {
   nodes     NodeSet,
             -- a lane made up of two or more
             -- node points and any attributes 
             -- defined in those nodes
   computed  ComputedLane,
             -- a lane path computed by translating 
             -- the data defined by another lane
   ...
   }
 
 
 
-- DF_Node_LLmD_64b (Desc Name) Record 49
Node-LLmD-64b ::=  SEQUENCE {
   lon  Longitude,
   lat  Latitude
   }
 
 
 
-- DF_NodeOffsetPoint (Desc Name) Record 50
NodeOffsetPoint ::=  CHOICE {
   -- Nodes with X,Y content
   node-XY1         Node-XY-20b,    -- node is within   5.11m of last node
   node-XY2         Node-XY-22b,    -- node is within  10.23m of last node
   node-XY3         Node-XY-24b,    -- node is within  20.47m of last node
   node-XY4         Node-XY-26b,    -- node is within  40.96m of last node
   node-XY5         Node-XY-28b,    -- node is within  81.91m of last node
   node-XY6         Node-XY-32b,    -- node is within 327.67m of last node
   node-LatLon      Node-LLmD-64b,  -- node is a full 32b Lat/Lon range
   node-Regional    RegionalNodeOffsetPoint
                                    -- node which follows is of a 
                                    -- regional definition type 
   }
 
 
 
-- DF_NodeSet (Desc Name) Record 51
NodeSet ::=  SEQUENCE (SIZE(2..63)) OF Node
 
 
 
-- DF_Node_XY_20b (Desc Name) Record 52
Node-XY-20b ::=  SEQUENCE {
   x  Offset-B10,
   y  Offset-B10
   }
 
 
 
-- DF_Node_XY_22b (Desc Name) Record 53
Node-XY-22b ::=  SEQUENCE {
   x  Offset-B11,
   y  Offset-B11
   }
 
 
 
-- DF_Node_XY_24b (Desc Name) Record 54
Node-XY-24b ::=  SEQUENCE {
   x  Offset-B12,
   y  Offset-B12
   }
 
 
 
-- DF_Node_XY_26b (Desc Name) Record 55
Node-XY-26b ::=  SEQUENCE {
   x  Offset-B13,
   y  Offset-B13
   }
 
 
 
-- DF_Node_XY_28b (Desc Name) Record 56
Node-XY-28b ::=  SEQUENCE {
   x  Offset-B14,
   y  Offset-B14
   }
 
 
 
-- DF_Node_XY_32b (Desc Name) Record 57
Node-XY-32b ::=  SEQUENCE {
   x  Offset-B16,
   y  Offset-B16
   }
 
 
 
-- DF_Offsets (Desc Name) Record 58
Offsets ::= OCTET STRING (SIZE(4..8)) 
   -- Made up of 
   -- SEQUENCE {
   -- xOffset  INTEGER (-32767..32767), 
   -- yOffset  INTEGER (-32767..32767),
   -- if 6 or 8 bytes in length:
   -- zOffset  INTEGER (-32767..32767) OPTIONAL,
            -- all above in signed values where 
            -- the LSB is in units of 1.0 cm   
  
   -- if 8 bytes in length:
   -- width    LaneWidth               OPTIONAL
   -- a length of 7 bytes is never used
   -- }
 
 
 
-- DF_OverlayLaneList (Desc Name) Record 59
OverlayLaneList ::=  SEQUENCE (SIZE(1..5)) OF LaneID
   -- The unique ID numbers for any lane object which have
   -- spatial paths that overlay (run on top of, and not
   -- simply cross with) the current lane.
   -- Such as a train path that overlays a motor vehicle
   -- lane object for a roadway segment.
 
 
 
-- DF_PathHistory (Desc Name) Record 60
PathHistory ::=  SEQUENCE {
   initialPosition  FullPositionVector   OPTIONAL,
   currGPSstatus    GPSstatus            OPTIONAL,   
   itemCnt          Count                OPTIONAL,   
                    -- Limited to range 1 to 23
                    -- number of points in set to follow
   crumbData  CHOICE {
              -- select one of the possible data sets to be used
   
              pathHistoryPointSets-01 SEQUENCE (SIZE(1..23)) OF 
                    PathHistoryPointType-01,
                    -- made up of sets of the: PathHistoryPointType-1
                    -- a set of all data elements, it is 
                    -- non-uniform in size, each item tagged in BER
   
              pathHistoryPointSets-02 OCTET STRING (SIZE(15..345)), 
                    -- made up of sets of the: PathHistoryPointType-02
                    -- sets of all data elements including:
                    -- lat, long, elev, time, accuracy, heading, and speed
                    -- offsets sent as a packed blob of 15 bytes per point
           
              pathHistoryPointSets-03 OCTET STRING (SIZE(12..276)), 
                    -- made up of sets of the: PathHistoryPointType-03
                    -- sets of the following data elements:
                    -- lat, long, elev, time, and accuracy
                    -- offsets sent as a packed blob of 12 bytes per point
  
              pathHistoryPointSets-04 OCTET STRING (SIZE(8..184)), 
                    -- made up of sets of the: PathHistoryPointType-04
                    -- sets of the following data elements:
                    -- lat, long, elev, and time
                    -- offsets sent as a packed blob of 8 bytes per point
   
              pathHistoryPointSets-05 OCTET STRING (SIZE(10..230)), 
                    -- made up of sets of the: PathHistoryPointType-05
                    -- sets of the following data elements:
                    -- lat, long, elev, and accuracy
                    -- offsets sent as a packed blob of 10 bytes per point
   
              pathHistoryPointSets-06 OCTET STRING (SIZE(6..138)), 
                    -- made up of sets of the: PathHistoryPointType-06
                    -- sets of the following data elements:
                    -- lat, long, and elev
                    -- offsets sent as a packed blob of 6 bytes per point
   
              pathHistoryPointSets-07 OCTET STRING (SIZE(11..242)), 
                    -- made up of sets of the: PathHistoryPointType-07
                    -- sets of the following data elements:
                    -- lat, long, time, and accuracy
                    -- offsets sent as a packed blob of 10.5 bytes per point
   
              pathHistoryPointSets-08 OCTET STRING (SIZE(7..161)), 
                    -- made up of sets of the: PathHistoryPointType-08
                    -- sets of the following data elements:
                    -- lat, long, and time
                    -- offsets sent as a packed blob of 7 bytes per point
   
              pathHistoryPointSets-09 OCTET STRING (SIZE(9..196)), 
                    -- made up of sets of the: PathHistoryPointType-09
                    -- sets of the following data elements:
                    -- lat, long, and accuracy
                    -- offsets sent as a packed blob of 8.5 bytes per point
   
              pathHistoryPointSets-10 OCTET STRING (SIZE(5..104))   
                    -- made up of sets of the: PathHistoryPointType-10
                    -- sets of the following data elements:
                    -- lat and long
                    -- offsets sent as a packed blob of 4.5 bytes per point

              }, 
   ... -- # LOCAL_CONTENT
   }
 
 
 
-- DF_PathHistoryPointType-01 (Desc Name) Record 61
PathHistoryPointType-01 ::=  SEQUENCE {
   latOffset  INTEGER (-131072..131071), 
               -- in 1/10th micro degrees 
               -- value  131071 to be used for  131071 or greater
               -- value -131071 to be used for -131071 or less
               -- value -131072 to be used for unavailable lat or long

   longOffset INTEGER (-131072..131071), 
               -- in 1/10th micro degrees 
               -- value  131071 to be used for  131071 or greater
               -- value -131071 to be used for -131071 or less
               -- value -131072 to be used for unavailable lat or long

    elevationOffset INTEGER (-2048..2047) OPTIONAL,  
               -- LSB units of of 10 cm
               -- value  2047 to be used for  2047 or greater
               -- value -2047 to be used for -2047 or greater
               -- value -2048 to be unavailable

    timeOffset INTEGER (1..65535) OPTIONAL,
               -- LSB units of of 10 mSec  
               -- value  65534 to be used for 65534 or greater
               -- value  65535 to be unavailable

    posAccuracy PositionalAccuracy OPTIONAL, 
               -- four packed bytes

    heading    INTEGER (-128..127) OPTIONAL, 
               -- where the LSB is in 
               -- units of 1.5 degrees 
               -- value -128 for unavailable
               -- not an offset value

    speed      TransmissionAndSpeed  OPTIONAL 
               -- upper bits encode transmission 
               -- where the LSB is in 
               -- units of 0.02 m/s
               -- not an offset value 
   }
 
 
 
-- DF_PathHistoryPointType-02 (Desc Name) Record 62
PathHistoryPointType-02 ::= OCTET STRING (SIZE(15)) 
   -- To be made up of packed bytes as follows: 
   -- latOffset  INTEGER (-131072..131071) (18 signed bits)
   -- longOffset INTEGER (-131072..131071) (18 signed bits)
    -- in 1/10th micro degrees 
    -- value  131071 to be used for  131071 or greater
    -- value -131071 to be used for -131071 or less
    -- value -131072 to be used for unavailable lat or long

   -- elevationOffset    INTEGER (-2048..2047), (12 signed bits)
    -- LSB units of 10 cm
    -- value  2047 to be used for  2047 or greater
    -- value -2047 to be used for -2047 or greater
    -- value -2048 to be unavailable

   -- timeOffset INTEGER (0..65535), (16 unsigned bits)
    -- LSB units of of 10 mSec   
    -- value  65534 to be used for 65534 or greater
    -- value  65535 to be unavailable

   -- accuracy   PositionalAccuracy 
    -- four packed bytes

   -- heading    INTEGER (-128..127), (8 signed bits)
    -- where the LSB is in 
    -- units of 1.5 degrees 
    -- value -128 for unavailable
    -- not an offset value

   -- speed      TransmissionAndSpeed (16 encoded bits) 
    -- upper bits encode transmission 
    -- where the LSB is in 
    -- units of 0.02 m/s
    -- not an offset value
 
 
 
-- DF_PathHistoryPointType-03 (Desc Name) Record 63
PathHistoryPointType-03 ::= OCTET STRING (SIZE(12)) 
   -- To be made up of packed bytes as follows: 
   -- latOffset  INTEGER (-131072..131071) (18 signed bits)
   -- longOffset INTEGER (-131072..131071) (18 signed bits)
    -- in 1/10th micro degrees 
    -- value  131071 to be used for  131071 or greater
    -- value -131071 to be used for -131071 or less
    -- value -131072 to be used for unavailable lat or long

   -- elevationOffset    INTEGER (-2048..2047), (12 signed bits)
    -- LSB units of 10 cm
    -- value  2047 to be used for  2047 or greater
    -- value -2047 to be used for -2047 or greater
    -- value -2048 to be unavailable

   -- timeOffset INTEGER (0..65535), (16 unsigned bits)
    -- LSB units of of 10 mSec   
    -- value  65534 to be used for 65534 or greater
    -- value  65535 to be unavailable

   -- accuracy   PositionalAccuracy 
    -- four packed bytes
 
 
 
-- DF_PathHistoryPointType-04 (Desc Name) Record 64
PathHistoryPointType-04 ::= OCTET STRING (SIZE(8)) 
   -- To be made up of packed bytes as follows: 
   -- latOffset  INTEGER (-131072..131071) (18 signed bits)
   -- longOffset INTEGER (-131072..131071) (18 signed bits)
    -- in 1/10th micro degrees 
    -- value  131071 to be used for  131071 or greater
    -- value -131071 to be used for -131071 or less
    -- value -131072 to be used for unavailable lat or long

   -- elevationOffset    INTEGER (-2048..2047), (12 signed bits)
    -- LSB units of 10 cm
    -- value  2047 to be used for  2047 or greater
    -- value -2047 to be used for -2047 or greater
    -- value -2048 to be unavailable

   -- timeOffset INTEGER (0..65535), (16 unsigned bits)
    -- LSB units of of 10 mSec   
    -- value  65534 to be used for 65534 or greater
    -- value  65535 to be unavailable
 
 
 
-- DF_PathHistoryPointType-05 (Desc Name) Record 65
PathHistoryPointType-05 ::= OCTET STRING (SIZE(10)) 
   -- To be made up of packed bytes as follows: 
   -- latOffset  INTEGER (-131072..131071) (18 signed bits)
   -- longOffset INTEGER (-131072..131071) (18 signed bits)
    -- in 1/10th micro degrees 
    -- value  131071 to be used for  131071 or greater
    -- value -131071 to be used for -131071 or less
    -- value -131072 to be used for unavailable lat or long

   -- elevationOffset    INTEGER (-2048..2047), (12 signed bits)
    -- LSB units of 10 cm
    -- value  2047 to be used for  2047 or greater
    -- value -2047 to be used for -2047 or greater
    -- value -2048 to be unavailable

   -- accuracy   PositionalAccuracy 
    -- four packed bytes
 
 
 
-- DF_PathHistoryPointType-06 (Desc Name) Record 66
PathHistoryPointType-06 ::= OCTET STRING (SIZE(6)) 
   -- To be made up of packed bytes as follows: 
   -- latOffset  INTEGER (-131072..131071) (18 signed bits)
   -- longOffset INTEGER (-131072..131071) (18 signed bits)
    -- in 1/10th micro degrees 
    -- value  131071 to be used for  131071 or greater
    -- value -131071 to be used for -131071 or less
    -- value -131072 to be used for unavailable lat or long

   -- elevationOffset    INTEGER (-2048..2047), (12 signed bits)
    -- LSB units of 10 cm
    -- value  2047 to be used for  2047 or greater
    -- value -2047 to be used for -2047 or greater
    -- value -2048 to be unavailable
 
 
 
-- DF_PathHistoryPointType-07 (Desc Name) Record 67
PathHistoryPointType-07 ::= OCTET STRING (SIZE(11)) -- in fact 10.5
   -- To be made up of packed bytes as follows: 
   -- latOffset  INTEGER (-131072..131071) (18 signed bits)
   -- longOffset INTEGER (-131072..131071) (18 signed bits)
    -- in 1/10th micro degrees 
    -- value  131071 to be used for  131071 or greater
    -- value -131071 to be used for -131071 or less
    -- value -131072 to be used for unavailable lat or long

   -- timeOffset INTEGER (0..65535), (16 unsigned bits)
    -- LSB units of of 10 mSec   
    -- value  65534 to be used for 65534 or greater
    -- value  65535 to be unavailable

   -- accuracy   PositionalAccuracy 
    -- four packed bytes
 
 
 
-- DF_PathHistoryPointType-08 (Desc Name) Record 68
PathHistoryPointType-08 ::= OCTET STRING (SIZE(7)) -- in fact 6.5 
   -- To be made up of packed bytes as follows: 
   -- latOffset  INTEGER (-131072..131071) (18 signed bits)
   -- longOffset INTEGER (-131072..131071) (18 signed bits)
    -- in 1/10th micro degrees 
    -- value  131071 to be used for  131071 or greater
    -- value -131071 to be used for -131071 or less
    -- value -131072 to be used for unavailable lat or long

   -- timeOffset INTEGER (0..65535), (16 unsigned bits)
    -- LSB units of of 10 mSec   
    -- value  65534 to be used for 65534 or greater
    -- value  65535 to be unavailable
 
 
 
-- DF_PathHistoryPointType-09 (Desc Name) Record 69
PathHistoryPointType-09 ::= OCTET STRING (SIZE(9)) -- in fact 8.5
   -- To be made up of packed bytes as follows: 
   -- latOffset  INTEGER (-131072..131071) (18 signed bits)
   -- longOffset INTEGER (-131072..131071) (18 signed bits)
    -- in 1/10th micro degrees 
    -- value  131071 to be used for  131071 or greater
    -- value -131071 to be used for -131071 or less
    -- value -131072 to be used for unavailable lat or long

   -- accuracy   PositionalAccuracy 
    -- four packed bytes
 
 
 
-- DF_PathHistoryPointType-10 (Desc Name) Record 70
PathHistoryPointType-10 ::= OCTET STRING (SIZE(5))   -- in fact 4.5 
   -- To be made up of packed bytes as follows: 
   -- latOffset  INTEGER (-131072..131071) (18 signed bits)
   -- longOffset INTEGER (-131072..131071) (18 signed bits)
    -- in 1/10th micro degrees 
    -- value  131071 to be used for  131071 or greater
    -- value -131071 to be used for -131071 or less
    -- value -131072 to be used for unavailable lat or long
 
 
 
-- DF_PathPrediction (Desc Name) Record 71
PathPrediction ::=  SEQUENCE {
   radiusOfCurve INTEGER (-32767..32767), 
                 -- LSB units of 10cm
                 -- straight path to use value of 32767
   confidence    INTEGER (0..200), 
                 -- LSB units of 0.5 percent
  
   ... -- # LOCAL_CONTENT
   }
 
 
 
-- DF_Position3D (Desc Name) Record 72
Position3D ::=  SEQUENCE {
   lat         Latitude,   -- in 1/10th micro degrees
   long        Longitude,  -- in 1/10th micro degrees
   elevation   Elevation   OPTIONAL  
   }
 
 
 
-- DF_Position3D_2 (Desc Name) Record 73
Position3D-2 ::=  SEQUENCE {
   lat        Latitude,                -- in 1/10th micro degrees
   long       Longitude,               -- in 1/10th micro degrees
   elevation  Elevation2 OPTIONAL,     -- in 10 cm units
   regional   RegionalPosition3D OPTIONAL, 
                                  -- regional extensions
   ...
   }
 
 
 
-- DF_PositionalAccuracy (Desc Name) Record 74
PositionalAccuracy ::= OCTET STRING (SIZE(4)) 
  -- And the bytes defined as folllows

  -- Byte 1: semi-major accuracy at one standard dev 
  -- range 0-12.7 meter, LSB = .05m
  -- 0xFE=254=any value equal or greater than 12.70 meter
  -- 0xFF=255=unavailable semi-major value 

  -- Byte 2: semi-minor accuracy at one standard dev 
  -- range 0-12.7 meter, LSB = .05m
  -- 0xFE=254=any value equal or greater than 12.70 meter
  -- 0xFF=255=unavailable semi-minor value 

  -- Bytes 3-4: orientation of semi-major axis 
  -- relative to true north (0~359.9945078786 degrees)
  -- LSB units of 360/65535 deg  = 0.0054932479
  -- a value of 0x0000 =0 shall be 0 degrees
  -- a value of 0x0001 =1 shall be 0.0054932479degrees 
  -- a value of 0xFFFE =65534 shall be 359.9945078786 deg
  -- a value of 0xFFFF =65535 shall be used for orientation unavailable 
  -- (In NMEA GPGST)
 
 
 
-- DF_PositionConfidenceSet (Desc Name) Record 75
PositionConfidenceSet ::= OCTET STRING (SIZE(1)) 
-- To be encoded as:
-- SEQUENCE {
--   pos        PositionConfidence, 
--              -x- 4 bits, for both horizontal directions
--   elevation  ElevationConfidence 
--              -x- 4 bits
--   }
 
 
 
-- DF_PreemptPriorityList (Desc Name) Record 76
PreemptPriorityList ::=  SEQUENCE (SIZE(1..32)) OF RegionalSignalControlZone
 
 
 
-- DF_Regional_AdvisorySpeed (Desc Name) Record 77
RegionalAdvisorySpeed ::=  REGION.Reg-AdvisorySpeed
 
 
 
-- DF_Regional_ComputedLane (Desc Name) Record 78
RegionalComputedLane ::=  REGION.Reg-ComputedLane
 
 
 
-- DF_Regional_ConnectionManeuverAssist (Desc Name) Record 79
RegionalConnectionManeuverAssist ::=  REGION.Reg-ConnectionManeuverAssist
 
 
 
-- DF_Regional_GenericLane (Desc Name) Record 80
RegionalGenericLane ::=  REGION.Reg-GenericLane
 
 
 
-- DF_Regional_Intersection (Desc Name) Record 81
RegionalIntersection ::=  REGION.Reg-Intersection
 
 
 
-- DF_Regional_IntersectionState (Desc Name) Record 82
RegionalIntersectionState ::=  REGION.Reg-IntersectionState
 
 
 
-- DF_Regional_RegionalLaneAttributes (Desc Name) Record 83
RegionalLaneAttributes ::=  REGION.Reg-LaneAttributes
 
 
 
-- DF_Regional_LaneDataAttribute (Desc Name) Record 84
RegionalLaneDataAttribute ::=  REGION.Reg-LaneDataAttribute
 
 
 
-- DF_Regional_MapData (Desc Name) Record 85
RegionalMapData ::=  REGION.Reg-MapData
 
 
 
-- DF_Regional_MovementEvent (Desc Name) Record 86
RegionalMovementEvent ::=  REGION.Reg-MovementEvent
 
 
 
-- DF_Regional_MovementState (Desc Name) Record 87
RegionalMovementState ::=  REGION.Reg-MovementState
 
 
 
-- DF_Regional_RegionalNodeAttribute (Desc Name) Record 88
RegionalNodeAttribute ::=  REGION.Reg-NodeAttribute
 
 
 
-- DF_RegionalNodeAttributeList (Desc Name) Record 89
RegionalNodeAttributeList ::=  SEQUENCE (SIZE(1..8)) OF RegionalNodeAttribute
 
 
 
-- DF_Regional_NodeOffsetPoint (Desc Name) Record 90
RegionalNodeOffsetPoint ::=  REGION.Reg-NodeOffsetPoint
 
 
 
-- DF_Regional_Position3D (Desc Name) Record 91
RegionalPosition3D ::=  REGION.Reg-Position3D
 
 
 
-- DF_Regional_RestrictionUserType (Desc Name) Record 92
RegionalRestrictionUserType ::=  REGION.Reg-RestrictionUserType
 
 
 
-- DF_Regional_RoadSegment (Desc Name) Record 93
RegionalRoadSegment ::=  REGION.Reg-RoadSegment
 
 
 
-- DF_Regional_SignalControlZone (Desc Name) Record 94
RegionalSignalControlZone ::=  REGION.Reg-SignalControlZone
 
 
 
-- DF_Regional_SPAT (Desc Name) Record 95
RegionalSPAT ::=  REGION.Reg-SPAT
 
 
 
-- DF_RegionList (Desc Name) Record 96
RegionList ::=  SEQUENCE (SIZE(1..64)) OF RegionOffsets
   -- the Position3D ref point (starting point or anchor)
   -- is found in the outer object.
 
 
 
-- DF_RegionOffsets (Desc Name) Record 97
RegionOffsets ::=  SEQUENCE {
   xOffset  INTEGER (-32767..32767), 
   yOffset  INTEGER (-32767..32767),
   zOffset  INTEGER (-32767..32767) OPTIONAL
            -- all in signed values where 
            -- the LSB is in units of 1 meter  
   }
 
 
 
-- DF_RegionPointSet (Desc Name) Record 98
RegionPointSet ::=  SEQUENCE {
   anchor           Position3D  OPTIONAL, 
   nodeList         RegionList,      
                    -- path details of the regions outline        
   ...             
   }
 
 
 
-- DF_RegulatorySpeedLimit (Desc Name) Record 99
RegulatorySpeedLimit ::=  SEQUENCE {
   type        SpeedLimitType, 
               -- The type of regulatory speed which follows
   speed       Velocity
               -- The speed in units of 0.02 m/s
               -- when expressed in MPH this shall be rounded
               -- to the closest integer value
               -- See Remarks under the SpeedAdvice entry for
               -- converting and transmitting a speed expressed
               -- in MPH to units of 0.1 m/s
   }
 
 
 
-- DF_RestrictionClassAssignment (Desc Name) Record 100
RestrictionClassAssignment ::=  SEQUENCE {
   id       RestrictionClassID,
            -- the unique value (within an intersection or local region)
            -- that is assigned to this group of users
   users    RestrictionUserTypeList 
            -- The list of user types/classes 
            -- to which this restriction ID applies
   }
 
 
 
-- DF_RestrictionClassList (Desc Name) Record 101
RestrictionClassList ::=  SEQUENCE (SIZE(1..254)) OF
   RestrictionClassAssignment
 
 
 
-- DF_RestrictionUserType (Desc Name) Record 102
RestrictionUserType ::=  CHOICE {
   basicType   RestrictionAppliesTo,
               -- a set of the most commonly used types
   regional    RegionalRestrictionUserType 
               -- regional extensions
   }
 
 
 
-- DF_RestrictionUserTypeList (Desc Name) Record 103
RestrictionUserTypeList ::=  SEQUENCE (SIZE(1..16)) OF  RestrictionUserType
 
 
 
-- DF_RoadLaneSetList (Desc Name) Record 104
RoadLaneSetList ::=  SEQUENCE (SIZE(1..255)) OF GenericLane
 
 
 
-- DF_RoadSegment (Desc Name) Record 105
RoadSegment ::=  SEQUENCE {
   name        DescriptiveName OPTIONAL,
   id          RoadSegmentReferenceID,
                           -- a globally unique value for the segment
   revision    MsgCount,    
   -- Required default values about the descriptions to follow
   refPoint    Position3D-2, -- the reference from which subsequent
                           -- data points are offset until a new
                           -- point is used.
   laneWidth   LaneWidth OPTIONAL,   
                            -- Reference width used by all subsequent 
                            -- lanes unless a new width is given  
   speedLimits SpeedLimitList OPTIONAL, 
                            -- Reference regulatory speed limits
                            -- used by all subsequent 
                            -- lanes unless a new speed is given   
                            -- See Remarks under the SpeedAdvice entry 
                            -- for converting and transmitting a speed 
                            -- expressed in MPH to units of 0.1 m/s
   -- Data describing disruptions in the RoadSegment
   -- such as work zones etc will be added here;
   -- in the US the SAE ITIS codes would be used here
   -- The details regarding each lane type in the RoadSegment
   roadLaneSet RoadLaneSetList,   
  
--   roadLaneSet SEQUENCE (SIZE(1..255)) OF
--                  GenericLane,     
                           -- data about one or more lanes
                           -- (all lane geometry is here)
   
   regional     RegionalRoadSegment OPTIONAL, 
                           -- regional extensions
   ...
   }
 
 
 
-- DF_RoadSegmentList (Desc Name) Record 106
RoadSegmentList ::=  SEQUENCE (SIZE(1..32)) OF RoadSegment
 
 
 
-- DF_RoadSegmentReferenceID (Desc Name) Record 107
RoadSegmentReferenceID ::=  SEQUENCE {
   region  RoadRegulatorID OPTIONAL,
           -- a globally unique regional assignment value
           -- typical assigned to a regional DOT authority
           -- the value zero shall be used for testing needs
   id      RoadSegmentID
           -- a unique mapping to the road segment
           -- in question within the above region of use
           -- during its period of aggiment and use
           -- note that unlike intserectionID values, 
           -- this value can be reused by the region
   }
 
 
 
-- DF_RoadSignID (Desc Name) Record 108
RoadSignID ::=  SEQUENCE {
   position        Position3D,
                   -- Location of sign
   viewAngle       HeadingSlice,
                   -- Vehicle direction of travel while
                   -- facing active side of sign
   mutcdCode       MUTCDCode OPTIONAL,
                   -- Tag for MUTCD code or "generic sign" 
   crc             MsgCRC OPTIONAL 
                   -- Used to provide a check sum
   }
 
 
 
-- DF_RTCMHeader (Desc Name) Record 109
RTCMHeader ::= OCTET STRING  (SIZE(5))
   -- defined as:
   -- SEQUENCE {
   -- status     GPSstatus,
                 -- to occupy 1 byte 
   -- offsetSet  AntennaOffsetSet
                 -- to occupy 4 bytes 
   -- }
 
 
 
-- DF_RTCMmsg (Desc Name) Record 110
RTCMmsg ::=  SEQUENCE {
   rev       RTCM-Revision OPTIONAL,
   rtcmID    RTCM-ID       OPTIONAL,
             -- the message and sub-message type, as
             -- defined in the RTCM revision being used
   payload   RTCM-Payload,
             -- the payload bytes
   ... -- # LOCAL_CONTENT   
   }
 
 
 
-- DF_RTCMPackage (Desc Name) Record 111
RTCMPackage ::=  SEQUENCE {
   anchorPoint FullPositionVector OPTIONAL,
   -- precise observer position, if needed
    
   rtcmHeader  RTCMHeader,
   -- an octet blob consisting of: 
   -- one byte with:
   -- GPSstatus
   -- 4 bytes with:                 
   -- AntennaOffsetSet  containing x,y,z data         
          
   -- note that a max of 16 satellites are allowed
   msg1001    OCTET STRING (SIZE(16..124))  OPTIONAL, 
              -- pRange data GPS L1
   msg1002    OCTET STRING (SIZE(18..156))  OPTIONAL, 
              -- pRange data GPS L1

   msg1003    OCTET STRING (SIZE(21..210))  OPTIONAL, 
               -- pRange data GPS L1, L2
   msg1004    OCTET STRING (SIZE(24..258))  OPTIONAL, 
               -- pRange data GPS L1, L2

   msg1005    OCTET STRING (SIZE(19))  OPTIONAL, 
              -- observer station data
   msg1006    OCTET STRING (SIZE(21))  OPTIONAL, 
              -- observer station data

   msg1007    OCTET STRING (SIZE(5..36))  OPTIONAL, 
              -- antenna of observer station data
   msg1008    OCTET STRING (SIZE(6..68))  OPTIONAL, 
              -- antenna of observer station data
 
   msg1009    OCTET STRING (SIZE(16..136))  OPTIONAL, 
               -- pRange data GLONASS L1
   msg1010    OCTET STRING (SIZE(18..166))  OPTIONAL, 
               -- pRange data GLONASS L1

   msg1011    OCTET STRING (SIZE(21..222))  OPTIONAL, 
               -- pRange data GLONASS L1, L2
   msg1012    OCTET STRING (SIZE(24..268))  OPTIONAL, 
               -- pRange data GLONASS L1, L2

   msg1013    OCTET STRING (SIZE(13..27))  OPTIONAL, 
               -- system parameters data

   ..., -- # LOCAL_CONTENT
   -- The below items shall never be sent 
   -- over WSM stack encoding (other encodings may be used)
   -- and may be removed from the ASN 

   msg1014    OCTET STRING (SIZE(15))  OPTIONAL, 
              -- Network Aux Station (NAS) data
   msg1015    OCTET STRING (SIZE(13..69))  OPTIONAL, 
              -- Ionospheric Correction data
   msg1016    OCTET STRING (SIZE(14..81))  OPTIONAL, 
              -- Geometry Correction data
   msg1017    OCTET STRING (SIZE(16..115))  OPTIONAL, 
              -- Combined Ionospheric and Geometry data

   -- msg1018 is reserved at this time

   msg1019    OCTET STRING (SIZE(62))  OPTIONAL, 
              -- Satellite Ephermeris data
   msg1020    OCTET STRING (SIZE(45))  OPTIONAL, 
              -- Satellite Ephermeris data
   msg1021    OCTET STRING (SIZE(62))  OPTIONAL, 
              -- Helmert-Abridged Molodenski Transform data
   msg1022    OCTET STRING (SIZE(75))  OPTIONAL, 
              -- Molodenski-Badekas Transform data
   msg1023    OCTET STRING (SIZE(73))  OPTIONAL, 
              -- Ellipse Residuals data
   msg1024    OCTET STRING (SIZE(74))  OPTIONAL, 
              -- Plane-Grid Residuals data
   msg1025    OCTET STRING (SIZE(25))  OPTIONAL, 
              -- Non-Lab Conic Project data
   msg1026    OCTET STRING (SIZE(30))  OPTIONAL, 
              -- Lab Conic Conform Project data
   msg1027    OCTET STRING (SIZE(33))  OPTIONAL, 
              -- Ob Mercator Project data

   -- msg1028 is reserved at this time

   msg1029    OCTET STRING (SIZE(10..69))  OPTIONAL, 
              -- Unicode test type data
   msg1030    OCTET STRING (SIZE(14..105))  OPTIONAL, 
              -- GPS Residuals data
   msg1031    OCTET STRING (SIZE(15..107))  OPTIONAL, 
              -- GLONASS Residuals data
   msg1032    OCTET STRING (SIZE(20))  OPTIONAL, 
              -- Ref Station Position data

   -- Proprietary Data content (msg40xx to msg4095) 
   -- may be added as needed 

   ... -- # LOCAL_CONTENT
   }
 
 
 
-- DF_Sample (Desc Name) Record 112
Sample ::=  SEQUENCE {
   sampleStart  INTEGER(0..255),   --  Sample Starting Point
   sampleEnd    INTEGER(0..255)    --  Sample Ending Point
   }
 
 
 
-- DF_SegmentAttributeList (Desc Name) Record 113
SegmentAttributeList ::=  SEQUENCE (SIZE(1..8)) OF SegmentAttribute
 
 
 
-- DF_ShapePointSet (Desc Name) Record 114
ShapePointSet ::=  SEQUENCE {
   anchor           Position3D     OPTIONAL, 
   laneWidth        LaneWidth      OPTIONAL, 
   directionality   DirectionOfUse OPTIONAL, 
   nodeList         NodeList,      -- path details of the lane and width           
   ...             
   }
 
 
 
-- DF_SignalControlZone (Desc Name) Record 115
SignalControlZone ::=  SEQUENCE {
   name           DescriptiveName OPTIONAL,
                  -- used only for debugging 
   pValue         SignalReqScheme, 
                  -- preempt or priorty value (0..7),
                  -- and any strategy value to be used
   
   data           CHOICE {
   
         laneSet  SEQUENCE (SIZE(1..32)) OF LaneNumber, 
                  -- a seq of of defined LaneNumbers,
                  -- to be used with this p value
                  -- see thier nodelists for paths
   
         zones    SEQUENCE (SIZE(1..32)) OF SEQUENCE {
   
             enclosed  SEQUENCE (SIZE(1..32)) OF LaneNumber OPTIONAL, 
                              -- lanes in this region
             laneWidth        LaneWidth  OPTIONAL, 
             nodeList         NodeList,
                              -- path details of 
                              -- the region starting from 
                              -- the stop line
             ... 
             } 
             -- Note: unlike a nodelist for lanes, 
             -- zones may overlap by a considerable degree
        },
   ... -- # LOCAL_CONTENT
   }
 
 
 
-- DF_SignalRequest (Desc Name) Record 116
SignalRequest ::=  SEQUENCE {
   -- the regionally unique ID of the target intersection 
   id     IntersectionID,  --  intersection ID
   
   -- Below present only when canceling a prior request
   isCancel   SignalReqScheme OPTIONAL,  
   
   -- In typical use either a SignalReqScheme  
   -- or a lane number would be given, this
   -- indicates the scheme to use or the 
   -- path through the intersection
   -- to the degree it is known.
   -- Note that SignalReqScheme can hold either
   -- a preempt or a priority value. 
   requestedAction  SignalReqScheme OPTIONAL,  
                           --  preempt ID or the
                           --  priority ID 
                           --  (and strategy) 
   inLane      LaneNumber OPTIONAL,       
                           --  approach Lane
   outLane     LaneNumber OPTIONAL,       
                           --  egress Lane
   type        NTCIPVehicleclass, 
                           --  Two 4 bit nibbles as: 
                           --  NTCIP vehicle class type
                           --  NTCIP vehicle class level
   
   -- any validation string used by the system
   codeWord    CodeWord OPTIONAL,
   ...
   }
 
 
 
-- DF_Snapshot (Desc Name) Record 117
Snapshot ::=  SEQUENCE {
   thePosition  FullPositionVector,          
                -- data of the position and speed, 
   safetyExt    VehicleSafetyExtension OPTIONAL, 
   datSet       VehicleStatus          OPTIONAL,  
                -- a seq of data frames
                -- which encodes the data
  ... -- # LOCAL_CONTENT 
   }
 
 
 
-- DF_SnapshotDistance (Desc Name) Record 118
SnapshotDistance ::=  SEQUENCE {
   d1   INTEGER(0..999),   -- meters
   s1   INTEGER(0..50),    -- meters\second
   d2   INTEGER(0..999),   -- meters
   s2   INTEGER(0..50)     -- meters\second
   }
 
 
 
-- DF_SnapshotTime (Desc Name) Record 119
SnapshotTime ::=  SEQUENCE {
   t1   INTEGER(1..99),   
        -- m/sec - the instantaneous speed when the 
        -- calculation is performed
   s1   INTEGER(0..50),   
        -- seconds
   t2   INTEGER(1..99),  
        -- m/sec - the instantaneous speed when the 
        -- calculation is performed
   s2   INTEGER(0..50)    
        -- seconds
   }
 
 
 
-- DF_Speed_Heading_Throttle_Confidence (Desc Name) Record 120
SpeedandHeadingandThrottleConfidence ::= OCTET STRING (SIZE(1)) 
-- to be packed as follows: 
-- SEQUENCE {
--   heading   HeadingConfidence,   -x- 3 bits 
--   speed     SpeedConfidence,     -x- 3 bits 
--   throttle  ThrottleConfidence   -x- 2 bits
--   }
 
 
 
-- DF_ITIS_Phrase_SpeedLimit (Desc Name) Record 121
SpeedLimit ::=  SEQUENCE (SIZE(1..10)) OF SEQUENCE {
  item-sl CHOICE    {
       itis   ITIS.ITIScodes,
       text   IA5String  (SIZE(1..16))
       } -- # UNTAGGED
  }
 
 
 
-- DF_SpeedLimitList (Desc Name) Record 122
SpeedLimitList ::=  SEQUENCE (SIZE(1..9)) OF RegulatorySpeedLimit
 
 
 
-- DF_TimeChangeDetails (Desc Name) Record 123
TimeChangeDetails ::=  SEQUENCE {
   startTime   TimeMark           OPTIONAL,
               -- When this phase 1st started
   minEndTime  TimeMark,
               -- Expected shortest end time
   maxEndTime  TimeMark           OPTIONAL,
               -- Expected longer end time
   
   likelyTime  TimeMark           OPTIONAL,
               -- Best predicted value based on other data              
   confidence  TimeIntervalConfidence OPTIONAL,
               -- Applies to above time element only
   
   nextTime    TimeMark           OPTIONAL
               -- A rough estimate of time when 
               -- this phase may next occur again
               -- used to support various ECO driving power 
               -- management needs.
   }
 
 
 
-- DF_TransmissionAndSpeed (Desc Name) Record 124
TransmissionAndSpeed ::= OCTET STRING (SIZE(2)) 
    -- Bits 14~16 to be made up of the data element
    -- DE_TransmissionState 
    -- Bits 1~13 to be made up of the data element
    -- DE_Speed
 
 
 
-- DF_ValidRegion (Desc Name) Record 125
ValidRegion ::=  SEQUENCE {
   
   direction         HeadingSlice,
                     -- field of view over which this applies,
   extent            Extent OPTIONAL,  
                     -- the spatial distance over which this
                     -- message applies and should be presented 
                     -- to the driver
   area    CHOICE  {
      shapePointSet  ShapePointSet,
                     -- A short road segment
      circle         Circle,
                     -- A point and radius
      regionPointSet RegionPointSet 
                     -- Wide area enclosed regions
      }
   }
 
 
 
-- DF_VehicleIdent (Desc Name) Record 126
VehicleIdent ::=  SEQUENCE {
   name           DescriptiveName OPTIONAL,
                  -- a human readable name for debugging use
   vin            VINstring OPTIONAL,
                  -- vehicle VIN value
   ownerCode      IA5String(SIZE(1..32)) OPTIONAL,
                  -- vehicle owner code 
   id             TemporaryID OPTIONAL, 
                  -- same value used in the BSM
      
   vehicleType    VehicleType  OPTIONAL, 
   vehicleClass   CHOICE 
                  {
                  vGroup ITIS.VehicleGroupAffected,
                  rGroup ITIS.ResponderGroupAffected,
                  rEquip ITIS.IncidentResponseEquipment  
                  } OPTIONAL, 
   ... -- # LOCAL_CONTENT
   }
 
 
 
-- DF_VehicleSafetyExtension (Desc Name) Record 127
VehicleSafetyExtension ::=  SEQUENCE {
   events             EventFlags     OPTIONAL,
   pathHistory        PathHistory    OPTIONAL, 
   pathPrediction     PathPrediction OPTIONAL,
   theRTCM            RTCMPackage    OPTIONAL,
   ... -- # LOCAL_CONTENT
   }
 
 
 
-- DF_VehicleSize (Desc Name) Record 128
VehicleSize ::=  SEQUENCE {
   width     VehicleWidth,
   length    VehicleLength
   }  -- 3 bytes in length
 
 
 
-- DF_VehicleStatus (Desc Name) Record 129
VehicleStatus ::=  SEQUENCE { 
   lights          ExteriorLights OPTIONAL,                 -- Exterior Lights
   lightBar        LightbarInUse  OPTIONAL,                 -- PS Lights
   
   wipers   SEQUENCE {
         statusFront    WiperStatusFront,
         rateFront      WiperRate,
         statusRear     WiperStatusRear       OPTIONAL,
         rateRear       WiperRate             OPTIONAL
         } OPTIONAL,                                        -- Wipers
   
   brakeStatus  BrakeSystemStatus OPTIONAL, 
                   -- 2 bytes with the following in it:
                   --   wheelBrakes        BrakeAppliedStatus,
                   --                      -x- 4 bits
                   --   traction           TractionControlState,
                   --                      -x- 2 bits
                   --   abs                AntiLockBrakeStatus, 
                   --                      -x- 2 bits
                   --   scs                StablityControlStatus, 
                   --                      -x- 2 bits
                   --   brakeBoost         BrakeBoostApplied, 
                   --                      -x- 2 bits
                   --   spareBits
                   --                      -x- 4 bits
                   -- Note that is present in BSM Part I
                                                            -- Braking Data
   brakePressure   BrakeAppliedPressure  OPTIONAL,          -- Braking Pressure
   roadFriction    CoefficientOfFriction OPTIONAL,          -- Roadway Friction 
   
      
   sunData         SunSensor             OPTIONAL,          -- Sun Sensor        
   rainData        RainSensor            OPTIONAL,          -- Rain Sensor        
   airTemp         AmbientAirTemperature OPTIONAL,          -- Air Temperature    
   airPres         AmbientAirPressure    OPTIONAL,          -- Air Pressure
   
   steering   SEQUENCE {
         angle      SteeringWheelAngle,   
         confidence SteeringWheelAngleConfidence   OPTIONAL,    
         rate       SteeringWheelAngleRateOfChange OPTIONAL,   
         wheels     DrivingWheelAngle              OPTIONAL
         } OPTIONAL,                                        -- steering data
   
   accelSets  SEQUENCE {
         accel4way       AccelerationSet4Way           OPTIONAL, 
         vertAccelThres  VerticalAccelerationThreshold OPTIONAL, 
                                                       -- Wheel Exceeded point
         yawRateCon      YawRateConfidence             OPTIONAL, 
                                                        -- Yaw Rate Confidence
         hozAccelCon     AccelerationConfidence        OPTIONAL,     
                                                        -- Acceleration Confidence 
         confidenceSet   ConfidenceSet                 OPTIONAL
                                                       -- general ConfidenceSet 
         } OPTIONAL, 
                                  
   
   object     SEQUENCE {
         obDist          ObstacleDistance,          -- Obstacle Distance        
         obDirect        ObstacleDirection,         -- Obstacle Direction        
         dateTime        DDateTime                  -- time detected
         } OPTIONAL,                                        -- detected Obstacle data
   
   
   
   fullPos         FullPositionVector OPTIONAL,     -- complete set of time and
                                                    -- position, speed, heading
   throttlePos     ThrottlePosition OPTIONAL,
   speedHeadC      SpeedandHeadingandThrottleConfidence OPTIONAL,    
   speedC          SpeedConfidence OPTIONAL,
   
   vehicleData   SEQUENCE {    
         height        VehicleHeight,
         bumpers       BumperHeights,
         mass          VehicleMass,
         trailerWeight TrailerWeight,
         type          VehicleType 
         -- values for width and length are sent in BSM part I as well. 
         } OPTIONAL,                                        -- vehicle data
   
   vehicleIdent   VehicleIdent OPTIONAL,                    -- comm vehicle data
 
   j1939data      J1939data OPTIONAL,           -- Various SAE J1938 data items
     
   weatherReport SEQUENCE {    
         isRaining        NTCIP.EssPrecipYesNo,
         rainRate         NTCIP.EssPrecipRate       OPTIONAL,
         precipSituation  NTCIP.EssPrecipSituation  OPTIONAL,
         solarRadiation   NTCIP.EssSolarRadiation   OPTIONAL,
         friction         NTCIP.EssMobileFriction   OPTIONAL
         } OPTIONAL,                                        -- local weather data
      
   gpsStatus      GPSstatus          OPTIONAL,              -- vehicle's GPS
 
   ... -- # LOCAL_CONTENT OPTIONAL,        
   }
 
 
 
-- DF_VehicleStatusRequest (Desc Name) Record 130
VehicleStatusRequest ::=  SEQUENCE {
   dataType             VehicleStatusDeviceTypeTag, 
   subType              INTEGER (1..15)   OPTIONAL, 
   sendOnLessThenValue  INTEGER (-32767..32767) OPTIONAL, 
   sendOnMoreThenValue  INTEGER (-32767..32767) OPTIONAL, 
   sendAll              BOOLEAN OPTIONAL, 
   ... 
   }
 
 
 
-- DF_WiperStatus (Desc Name) Record 131
WiperStatus ::=  SEQUENCE {
   statusFront    WiperStatusFront,
   rateFront      WiperRate,
   statusRear     WiperStatusRear      OPTIONAL,
   rateRear       WiperRate            OPTIONAL
   }
 
 
 
-- DF_ITIS_Phrase_WorkZone (Desc Name) Record 132
WorkZone ::=  SEQUENCE (SIZE(1..10)) OF SEQUENCE {
  item-wk CHOICE    {
       itis   ITIS.ITIScodes,
       text   IA5String  (SIZE(1..16))
       } -- # UNTAGGED
  }
 
 
-- -_-_-_-_-_-_-_-_-_-_-_-_-_-_-_-_-_-_-_-_-_-_-_-_-_-_-_-_
-- 
-- Start of entries from table Data_Elements...
-- This table typically contains data element entries.
-- -_-_-_-_-_-_-_-_-_-_-_-_-_-_-_-_-_-_-_-_-_-_-_-_-_-_-_-_
-- 
 
 
-- DE_Acceleration (Desc Name) Record 1
Acceleration ::= INTEGER (-2000..2001) 
    -- LSB units are 0.01 m/s^2
   -- the value 2000 shall be used for values greater than 2000     
   -- the value -2000 shall be used for values less than -2000  
   -- a value of 2001 shall be used for Unavailable
 
 
 
-- DE_AccelerationConfidence (Desc Name) Record 2
AccelerationConfidence ::= ENUMERATED {
   unavailable  (0), -- B'000  Not Equipped or data is unavailable
   accl-100-00  (1), -- B'001  100  meters / second squared
   accl-010-00  (2), -- B'010  10   meters / second squared
   accl-005-00  (3), -- B'011  5    meters / second squared
   accl-001-00  (4), -- B'100  1    meters / second squared
   accl-000-10  (5), -- B'101  0.1  meters / second squared
   accl-000-05  (6), -- B'110  0.05 meters / second squared
   accl-000-01  (7)  -- B'111  0.01 meters / second squared
   } 
   -- Encoded as a 3 bit value
 
 
 
-- DE_AdvisorySpeedType (Desc Name) Record 3
AdvisorySpeedType ::= ENUMERATED {
    none,
    greenwave,
    ecoDrive,
    transit,
    ...  
    }
 
 
 
-- DE_AllowedManeuvers (Desc Name) Record 4
AllowedManeuvers ::= BIT STRING {
    -- With bits as defined:
    -- Allowed and maneuvers at path end (stop line)
    -- All maneuvers with bits not set are therefore prohibited !
    -- A value of zero shall be used for unknown, indicating no Maneuver
    maneuverStraightAllowed      (0), 
                                  -- a Straight movement is allowed in this lane
    maneuverLeftAllowed          (1),  
                                 -- a Left Turn movement is allowed in this lane
    maneuverRightAllowed         (2), 
                                 -- a Right Turn movement is allowed in this lane
    maneuverUTurnAllowed         (3), 
                                 -- a U turn movement is allowed in this lane
    maneuverLeftTurnOnRedAllowed (4), 
                                 -- a Stop, and then proceed when safe movement 
                                 -- is allowed in this lane  
    maneuverRightTurnOnRedAllowed (5), 
                                 -- a Stop, and then proceed when safe movement 
                                 -- is allowed in this lane  
    maneuverLaneChangeAllowed    (6), 
                                 -- a movement which changes to an outer lane 
                                 -- on the egress side is allowed in this lane
                                 -- (example: left into either outbound lane)
    maneuverNoStoppingAllowed    (7), 
                                 -- the vehicle should not stop at the stop line
                                 -- (example: a flashing green arrow)
    yieldAllwaysRequired         (8), 
                                 -- the allowed movements above are not protected 
                                 -- (example: an permanent yellow condition)
    goWithHalt                   (9), 
                                 -- after making a full stop, may proceed
    caution                      (10), 
                                 -- proceed past stop line with caution
    reserved1                    (11)
                                 -- used to align to 12 Bit Field
   
   } (SIZE(12))
 
 
 
-- DE_AmbientAirPressure (Barometric Pressure) (Desc Name) Record 5
AmbientAirPressure ::= INTEGER (0..255) 
   -- 8 Bits in hPa starting at 580 with a resolution of 
   -- 2 hPa resulting in a range of 580 to 1090
 
 
 
-- DE_AmbientAirTemperature (Desc Name) Record 6
AmbientAirTemperature ::= INTEGER (0..191) -- in deg C with a -40 offset
 
 
 
-- DE_Angle (Desc Name) Record 7
Angle ::= INTEGER (0..28800) 
   -- LSB of 0.0125 degrees
   -- A range of 0 to 359.9875 degrees
 
 
 
-- DE_AntiLockBrakeStatus (Desc Name) Record 8
AntiLockBrakeStatus ::= ENUMERATED {
   unavailable (0), -- B'00  Vehicle Not Equipped with ABS 
                    -- or ABS status is unavailable
   off         (1), -- B'01  Vehicle's ABS is Off
   on          (2), -- B'10  Vehicle's ABS is On (but not engaged)
   engaged     (3)  -- B'11  Vehicle's ABS is Engaged
   } 
   -- Encoded as a 2 bit value
 
 
 
-- DE_ApproachID (Desc Name) Record 9
ApproachID ::= INTEGER (0..15) -- zero to be used when valid value is unknown
 
 
 
-- DE_AuxiliaryBrakeStatus (Desc Name) Record 10
AuxiliaryBrakeStatus ::= ENUMERATED {
   unavailable (0), -- B'00  Vehicle Not Equipped with Aux Brakes 
                    -- or Aux Brakes status is unavailable
   off         (1), -- B'01  Vehicle's Aux Brakes are Off
   on          (2), -- B'10  Vehicle's Aux Brakes are On ( Engaged )
   reserved    (3)  -- B'11 
   } 
   -- Encoded as a 2 bit value
 
 
 
-- DE_J1939-71-Axle Location (Desc Name) Record 11
AxleLocation ::= INTEGER (0..127)
 
 
 
-- DE_J1939-71-Axle Weight (Desc Name) Record 12
AxleWeight ::= INTEGER (0..65535)
 
 
 
-- DE_BrakeAppliedPressure (Desc Name) Record 13
BrakeAppliedPressure ::= ENUMERATED {
   unavailable  (0),  -- B'0000 Not Equipped
                      -- or Brake Pres status is unavailable
   minPressure  (1),  -- B'0001 Minimum Braking Pressure
   bkLvl-2      (2),  -- B'0010
   bkLvl-3      (3),  -- B'0011   
   bkLvl-4      (4),  -- B'0100  
   bkLvl-5      (5),  -- B'0101
   bkLvl-6      (6),  -- B'0110
   bkLvl-7      (7),  -- B'0111
   bkLvl-8      (8),  -- B'1000
   bkLvl-9      (9),  -- B'1001
   bkLvl-10     (10), -- B'1010
   bkLvl-11     (11), -- B'1011
   bkLvl-12     (12), -- B'1100
   bkLvl-13     (13), -- B'1101
   bkLvl-14     (14), -- B'1110
   maxPressure  (15)  -- B'1111 Maximum Braking Pressure
   } 
   -- Encoded as a 4 bit value
 
 
 
-- DE_BrakeAppliedStatus (Desc Name) Record 14
BrakeAppliedStatus ::= BIT STRING {
   allOff      (0), -- B'0000  The condition All Off 
   leftFront   (1), -- B'0001  Left Front Active
   leftRear    (2), -- B'0010  Left Rear Active
   rightFront  (4), -- B'0100  Right Front Active
   rightRear   (8)  -- B'1000  Right Rear Active
   } -- to fit in 4 bits
 
 
 
-- DE_BrakeBoostApplied (Desc Name) Record 15
BrakeBoostApplied ::= ENUMERATED {
   unavailable   (0), -- Vehicle not equipped with brake boost
                      -- or brake boost data is unavailable
   off           (1), -- Vehicle's brake boost is off
   on            (2)  -- Vehicle's brake boost is on (applied)
   }
   -- Encoded as a 2 bit value
 
 
 
-- DE_BumperHeightFront (Desc Name) Record 16
BumperHeightFront ::= INTEGER (0..127) -- in units of 0.01 meters from ground surface.
 
 
 
-- DE_BumperHeightRear (Desc Name) Record 17
BumperHeightRear ::= INTEGER (0..127) -- in units of 0.01 meters from ground surface.
 
 
 
-- DE_J1939-71-Cargo Weight (Desc Name) Record 18
CargoWeight ::= INTEGER (0..65535)
 
 
 
-- DE_CodeWord (Desc Name) Record 19
CodeWord ::= OCTET STRING (SIZE(1..16)) 
   -- any octect string up to 16 bytes
 
 
 
-- DE_CoefficientOfFriction (Desc Name) Record 20
CoefficientOfFriction ::= INTEGER (0..50) 
   -- where 0 = 0.00 micro (frictonless)
   -- and 50 = 0.98 micro, in steps of 0.02
 
 
 
-- DE_Count (Desc Name) Record 21
Count ::= INTEGER (0..32)
 
 
 
-- DE_DDay (Desc Name) Record 22
DDay ::= INTEGER (0..31)  -- units of days
 
 
 
-- DE_DeltaAngle (Desc Name) Record 23
DeltaAngle ::= INTEGER (-150..150) 
   -- With an angle range from 
   -- negative 150 to positive 150 
   -- in one degree steps where zero is directly
   -- along the lane center line as defined by the
   -- two closest points
 
 
 
-- DE_DescriptiveName (Desc Name) Record 24
DescriptiveName ::= IA5String (SIZE(1..63))
 
 
 
-- DE_DHour (Desc Name) Record 25
DHour ::= INTEGER (0..31) -- units of hours
 
 
 
-- DE_DirectionOfUse (Desc Name) Record 26
DirectionOfUse ::= ENUMERATED {
   forward    (0), -- direction of travel follows node ordering 
   reverse    (1), -- direction of travel is the reverse of node ordering 
   both       (2), -- direction of travel allowed in both directions 
   ...
   }
 
 
 
-- DE_DMinute (Desc Name) Record 27
DMinute ::= INTEGER (0..63) -- units of minutes
 
 
 
-- DE_DMonth (Desc Name) Record 28
DMonth ::= INTEGER (0..15) -- units of months
 
 
 
-- DE_DOffset (Desc Name) Record 29
DOffset ::= INTEGER (-840..840) -- units of minutes from UTC time
 
 
 
-- DE_J1939-71-Drive Axle Lift Air Pressure (Desc Name) Record 30
DriveAxleLiftAirPressure ::= INTEGER (0..1000)
 
 
 
-- DE_J1939-71-Drive Axle Location (Desc Name) Record 31
DriveAxleLocation ::= INTEGER (0..255)
 
 
 
-- DE_J1939-71-Drive Axle Lube Pressure (Desc Name) Record 32
DriveAxleLubePressure ::= INTEGER (0..1000)
 
 
 
-- DE_J1939-71-Drive Axle Temperature (Desc Name) Record 33
DriveAxleTemperature ::= INTEGER (-40..210)
 
 
 
-- DE_DrivenLineOffsetLarge (Desc Name) Record 34
DrivenLineOffsetLg ::= INTEGER (-32767..32767) 
   -- LSB units are 1 cm.
 
 
 
-- DE_DrivenLineOffsetSmall (Desc Name) Record 35
DrivenLineOffsetSm ::= INTEGER (-2047..2047) 
   -- LSB units are 1 cm.
 
 
 
-- DE_DrivingWheelAngle (Desc Name) Record 36
DrivingWheelAngle ::= INTEGER (-127..127) 
   -- LSB units of 0.3333 degrees.  
   -- a range of 42.33 degrees each way
 
 
 
-- DE_DSecond (Desc Name) Record 37
DSecond ::= INTEGER (0..65535) -- units of miliseconds
 
 
 
-- DE_DSecond2 (Desc Name) Record 38
DSecond2 ::= INTEGER (0..65535) -- units of miliseconds
 
 
 
-- DE_DSRC_MessageID (Desc Name) Record 39
DSRCmsgID ::= ENUMERATED {
   reserved                        (0), 
   alaCarteMessage                 (1),  -- ACM
   basicSafetyMessage              (2),  -- BSM, heartbeat msg
   basicSafetyMessageVerbose       (3),  -- used for testing only
   commonSafetyRequest             (4),  -- CSR
   emergencyVehicleAlert           (5),  -- EVA
   intersectionCollisionAlert      (6),  -- ICA
   mapData                         (7),  -- MAP, GID, intersections 
   nmeaCorrections                 (8),  -- NMEA
   probeDataManagement             (9),  -- PDM
   probeVehicleData                (10), -- PVD
   roadSideAlert                   (11), -- RSA
   rtcmCorrections                 (12), -- RTCM
   signalPhaseAndTimingMessage     (13), -- SPAT
   signalRequestMessage            (14), -- SRM
   signalStatusMessage             (15), -- SSM
   travelerInformation             (16), -- TIM
   
   ... -- # LOCAL_CONTENT
   } 
   -- values to 127 reserved for std use
   -- values 128 to 255 reserved for local use
 
 
 
-- DE_DSRC_MessageID2 (Desc Name) Record 40
DSRCmsgID2 ::= INTEGER (0..255)
   -- DER forms
   reservedMessageId-D               DSRCmsgID2 ::=  0 --'00'H 
   alaCarteMessage-D                 DSRCmsgID2 ::=  1 --'01'H ACM
   -- alaCarteMessage-D is Retired, not to be used
   basicSafetyMessage-D              DSRCmsgID2 ::=  2 --'02'H BSM, heartbeat msg
   basicSafetyMessageVerbose-D       DSRCmsgID2 ::=  3 --'03'H For testing only
   commonSafetyRequest-D             DSRCmsgID2 ::=  4 --'04'H CSR
   emergencyVehicleAlert-D           DSRCmsgID2 ::=  5 --'05'H EVA
   intersectionCollisionAlert-D      DSRCmsgID2 ::=  6 --'06'H ICA
   mapData-D                         DSRCmsgID2 ::=  7 --'07'H MAP, intersections 
   -- mapData-D is Retired, not to be used
   nmeaCorrections-D                 DSRCmsgID2 ::=  8 --'08'H NMEA
   probeDataManagement-D             DSRCmsgID2 ::=  9 --'09'H PDM
   probeVehicleData-D                DSRCmsgID2 ::= 10 --'0A'H PVD
   roadSideAlert-D                   DSRCmsgID2 ::= 11 --'0B'H RSA
   rtcmCorrections-D                 DSRCmsgID2 ::= 12 --'0C'H RTCM
   signalPhaseAndTimingMessage-D     DSRCmsgID2 ::= 13 --'0D'H SPAT
   -- signalPhaseAndTimingMessage-D is Retired, not to be used
   signalRequestMessage-D            DSRCmsgID2 ::= 14 --'0E'H SRM
   signalStatusMessage-D             DSRCmsgID2 ::= 15 --'0F'H SSM
   travelerInformation-D             DSRCmsgID2 ::= 16 --'10'H TIM
   uperFrame-D                       DSRCmsgID2 ::= 17 --'11'H UPER frame
   -- UPER forms
   mapData-P                         DSRCmsgID2 ::= 18 --'12'H MAP, intersections 
   signalPhaseAndTimingMessage-P     DSRCmsgID2 ::= 19 --'13'H SPAT
                           
   -- values to 127 reserved for std use
   -- values 128 to 255 reserved for local use
 
 
 
-- DE_DSRC_MessageSubID (Desc Name) Record 41
DSRCmsgSubID ::= INTEGER (0..255) -- to be set to zero when used at this time
 
 
 
-- DE_DYear (Desc Name) Record 42
DYear ::= INTEGER (0..9999) -- units of years
 
 
 
-- DE_Elevation (Desc Name) Record 43
Elevation ::= OCTET STRING (SIZE(2))
   -- 1 decimeter LSB (10 cm) 
   -- Encode elevations from 0 to 6143.9 meters 
   -- above the reference ellipsoid as 0x0000 to 0xEFFF.  
   -- Encode elevations from -409.5 to -0.1 meters, 
   -- i.e. below the reference ellipsoid, as 0xF001 to 0xFFFF
   -- unknown as 0xF000
 
 
 
-- DE_Elevation2 (Desc Name) Record 44
Elevation2 ::= INTEGER (-4096..61439) 
    -- In units of 10 cm steps above or below the reference ellipsoid
    -- Providing a range of -409.5 to + 6143.9 meters
    -- The value -4096 shall be used when Unknown is to be sent
 
 
 
-- DE_ElevationConfidence (Desc Name) Record 45
ElevationConfidence ::= ENUMERATED {
   unavailable (0),  -- B'0000  Not Equipped or unavailable
   elev-500-00 (1),  -- B'0001  (500 m)
   elev-200-00 (2),  -- B'0010  (200 m)
   elev-100-00 (3),  -- B'0011  (100 m)
   elev-050-00 (4),  -- B'0100  (50 m)
   elev-020-00 (5),  -- B'0101  (20 m)
   elev-010-00 (6),  -- B'0110  (10 m)
   elev-005-00 (7),  -- B'0111  (5 m)
   elev-002-00 (8),  -- B'1000  (2 m)
   elev-001-00 (9),  -- B'1001  (1 m)
   elev-000-50 (10), -- B'1010  (50 cm)
   elev-000-20 (11), -- B'1011  (20 cm)
   elev-000-10 (12), -- B'1100  (10 cm)
   elev-000-05 (13), -- B'1101  (5 cm)
   elev-000-02 (14), -- B'1110  (2 cm)
   elev-000-01 (15)  -- B'1111  (1 cm)
   } 
   -- Encoded as a 4 bit value
 
 
 
-- DE_EmergencyDetails (Desc Name) Record 46
EmergencyDetails ::= INTEGER (0..63) 
   -- First two bit (MSB set to zero.
   -- Combining these 3 items in the remaning 6 bits
   -- sirenUse        SirenInUse                 
   -- lightsUse       LightbarInUse              
   -- multi           MultiVehicleReponse
 
 
 
-- DE_EventFlags (Desc Name) Record 47
EventFlags ::= INTEGER (0..8192) 
-- With bits as defined:
   eventHazardLights               EventFlags ::= 1
   eventStopLineViolation          EventFlags ::= 2 -- Intersection Violation   
   eventABSactivated               EventFlags ::= 4
   eventTractionControlLoss        EventFlags ::= 8
   eventStabilityControlactivated  EventFlags ::= 16
   eventHazardousMaterials         EventFlags ::= 32
   eventEmergencyResponse          EventFlags ::= 64
   eventHardBraking                EventFlags ::= 128
   eventLightsChanged              EventFlags ::= 256
   eventWipersChanged              EventFlags ::= 512
   eventFlatTire                   EventFlags ::= 1024
   eventDisabledVehicle            EventFlags ::= 2048
   eventAirBagDeployment           EventFlags ::= 4096
 
 
 
-- DE_Extent (Desc Name) Record 48
Extent ::= ENUMERATED {
    useInstantlyOnly   (0),
    useFor3meters      (1),
    useFor10meters     (2),
    useFor50meters     (3),
    useFor100meters    (4),
    useFor500meters    (5),
    useFor1000meters   (6),
    useFor5000meters   (7),
    useFor10000meters  (8),
    useFor50000meters  (9),
    useFor100000meters (10),
    forever            (127)  -- very wide area
    }
    -- encode as a single byte
 
 
 
-- DE_ExteriorLights (Desc Name) Record 49
ExteriorLights ::= INTEGER (0..256) 
-- With bits as defined:
   allLightsOff              ExteriorLights ::= 0  
                             -- B'0000-0000  
   lowBeamHeadlightsOn       ExteriorLights ::= 1  
                             -- B'0000-0001
   highBeamHeadlightsOn      ExteriorLights ::= 2 
                             -- B'0000-0010
   leftTurnSignalOn          ExteriorLights ::= 4  
                             -- B'0000-0100
   rightTurnSignalOn         ExteriorLights ::= 8  
                             -- B'0000-1000
   hazardSignalOn            ExteriorLights ::= 12  
                             -- B'0000-1100
   automaticLightControlOn   ExteriorLights ::= 16  
                             -- B'0001-0000
   daytimeRunningLightsOn    ExteriorLights ::= 32  
                             -- B'0010-0000
   fogLightOn                ExteriorLights ::= 64 
                             -- B'0100-0000
   parkingLightsOn           ExteriorLights ::= 128  
                             -- B'1000-0000
 
 
 
-- DE_FurtherInfoID (Desc Name) Record 50
FurtherInfoID ::= OCTET STRING (SIZE(2))
   -- a link to any other incident 
   -- information data that may be available 
   -- in the normal ATIS incident description 
   -- or other messages
   -- two value bytes in length
 
 
 
-- DE_GPSstatus (Desc Name) Record 51
GPSstatus ::= BIT STRING {
   unavailable               (0), -- Not Equipped or unavailable
   isHealthy                 (1),
   isMonitored               (2),
   baseStationType           (3), -- Set to zero if a moving base station,
                                  -- set to one if it is a fixed base station 
   aPDOPofUnder5             (4), -- A dilution of precision greater then 5
   inViewOfUnder5            (5), -- Less then 5 satellites in view
   localCorrectionsPresent   (6),
   networkCorrectionsPresent (7)
   } -- (SIZE(1))
 
 
 
-- DE_Heading (Desc Name) Record 52
Heading ::= INTEGER (0..28800) 
   -- LSB of 0.0125 degrees
   -- A range of 0 to 359.9875 degrees
 
 
 
-- DE_HeadingConfidence (Desc Name) Record 53
HeadingConfidence ::= ENUMERATED {
   unavailable (0), -- B'000  Not Equipped or unavailable
   prec45deg   (1), -- B'001  45   degrees 
   prec10deg   (2), -- B'010  10   degrees
   prec05deg   (3), -- B'011  5    degrees
   prec01deg   (4), -- B'100  1    degrees
   prec0-1deg  (5), -- B'101  0.1  degrees
   prec0-05deg (6), -- B'110  0.05 degrees
   prec0-01deg (7)  -- B'111  0.01 degrees
   } 
   -- Encoded as a 3 bit value
 
 
 
-- DE_HeadingSlice (Desc Name) Record 54
HeadingSlice ::= OCTET STRING (SIZE(2))  
   -- Each bit 22.5 degree starting from 
   -- North and moving Eastward (clockwise)
   
   --  Define global enums for this entry
   noHeading                HeadingSlice ::= '0000'H
   allHeadings              HeadingSlice ::= 'FFFF'H
   
   from000-0to022-5degrees  HeadingSlice ::= '0001'H
   from022-5to045-0degrees  HeadingSlice ::= '0002'H
   from045-0to067-5degrees  HeadingSlice ::= '0004'H
   from067-5to090-0degrees  HeadingSlice ::= '0008'H
   
   from090-0to112-5degrees  HeadingSlice ::= '0010'H
   from112-5to135-0degrees  HeadingSlice ::= '0020'H
   from135-0to157-5degrees  HeadingSlice ::= '0040'H
   from157-5to180-0degrees  HeadingSlice ::= '0080'H
   
   from180-0to202-5degrees  HeadingSlice ::= '0100'H
   from202-5to225-0degrees  HeadingSlice ::= '0200'H
   from225-0to247-5degrees  HeadingSlice ::= '0400'H
   from247-5to270-0degrees  HeadingSlice ::= '0800'H
   
   from270-0to292-5degrees  HeadingSlice ::= '1000'H
   from292-5to315-0degrees  HeadingSlice ::= '2000'H
   from315-0to337-5degrees  HeadingSlice ::= '4000'H
   from337-5to360-0degrees  HeadingSlice ::= '8000'H
 
 
 
-- DE_IntersectionID (Desc Name) Record 55
IntersectionID ::= INTEGER (0..65535)
   -- The values zero through 255 are allocated for testing purposes
   -- Note that the value assign to an intersection will be
   -- unique within a given regional ID only
 
 
 
-- DE_IntersectionStatusObject (Desc Name) Record 56
IntersectionStatusObject ::= BIT STRING {
    manualControlIsEnabled                (0),
      -- Timing reported is per programmed values, etc but person
      -- at cabinet can manually request that certain intervals are
      -- terminated early (e.g. green).
    stopTimeIsActivated                   (1),
      -- And all counting/timing has stopped.
    failureFlash                          (2), 
      -- Above to be used for any detected hardware failures, 
      -- e.g. conflict monitor as well as for police flash 
    preemptIsActive                       (3),
    transitSignalPriorityIsActive         (4),   
      -- Refered to as TSP
	 
    -- Additional states
    fixedTimeOperation                    (5),
      -- Schedule of signals is based on time only 
      -- (i.e. the state can be calculated)
    trafficDependentOperation             (6),
      -- Operation is based on different levels of traffic parameters 
      -- (requests, duration of gaps or more complex parameters)
    standbyOperation                      (7),
      -- Controller: partially switched off or partially amber flashing
    failureMode                           (8),
      -- Controller has a problem or failure in operation
    off                                   (9),
      -- Controller is switched off
	 
    -- Related to MAP an SPAT bindings
    recentMAPmessageUpdate                (10),
      -- Map revision with content changes
    recentChangeInMAPassignedLanesIDsUsed (11),
      -- Change in MAP's assigned lanes used (lane changes)
      -- Changes in the active lane list description
    noValidMAPisAvailableAtThisTime       (12),
      -- MAP (and vaious lanes indexes) not available
    noValidSPATisAvailableAtThisTime      (13)
      -- SPAT system is not working at this time
    
    -- Bit values (14,15) reserved at ths time and shall be zero
    } (SIZE(16))
 
 
 
-- DE_LaneAttributes-Barrier (Desc Name) Record 57
LaneAttributes-Barrier ::= BIT STRING {
   -- With bits as defined:
   median-RevocableLane     (0),
                            -- this lane may be activated or not based
                            -- on the current SPAT message contents
                            -- if not asserted, the lane is ALWAYS present
   median                   (1),
   whiteLineHashing         (2),
   stripedLines             (3),
   doubleStripedLines       (4),
   trafficCones             (5),
   constructionBarrier      (6),
   trafficChannels          (7),
   lowCurbs                 (8),
   highCurbs                (9)
   -- Bits 10~15 reserved and set to zero
   } (SIZE (16))
 
 
 
-- DE_LaneAttributes-Bike (Desc Name) Record 58
LaneAttributes-Bike ::= BIT STRING {
   -- With bits as defined:
   bikeRevocableLane       (0),
                           -- this lane may be activated or not based
                           -- on the current SPAT message contents
                           -- if not asserted, the lane is ALWAYS present
   pedestrianUseAllowed    (1),
                           -- The path allows pedestrian traffic, 
                           -- if not set, this mode is prohibited
   isBikeFlyOverLane       (2),
                           -- path of lane is not at grade
   fixedCycleTime          (3),
                           -- the phases use preset times
                           -- i.e. there is not a 'push to cross' button
   biDirectionalCycleTimes (4),
                           -- ped walk phases use different SignalGroupID
                           -- for each direction. The first SignalGroupID
                           -- in the first Connection represents 'inbound'
                           -- flow (the direction of travel towards the first 
                           -- node point) while second SignalGroupID in the 
                           -- next Connection entry represents the 'outbound'
                           -- flow. And use of RestrictionClassID entires
                           -- in the Connect follow this same pattern in pairs.
   isolatedByBarrier       (5),
   unsignalizedSegmentsPresent  (6)
                           -- The lane path consists of one of more segments
                           -- which are not part of a signal group ID

   -- Bits 7~15 reserved and set to zero
   } (SIZE (16))
 
 
 
-- DE_LaneAttributes-Crosswalk (Desc Name) Record 59
LaneAttributes-Crosswalk ::= BIT STRING { 
   -- With bits as defined:
   -- MUTCD provides no suitable "types" to use here
   crosswalkRevocableLane  (0),
                           -- this lane may be activated or not based
                           -- on the current SPAT message contents
                           -- if not asserted, the lane is ALWAYS present
   bicyleUseAllowed        (1),
                           -- The path allows bicycle traffic, 
                           -- if not set, this mode is prohibited
   isXwalkFlyOverLane      (2),
                           -- path of lane is not at grade
   fixedCycleTime          (3),
                           -- ped walk phases use preset times
                           -- i.e. there is not a 'push to cross' button
   biDirectionalCycleTimes (4),
                           -- ped walk phases use different SignalGroupID
                           -- for each direction. The first SignalGroupID
                           -- in the first Connection represents 'inbound'
                           -- flow (the direction of travel towards the first 
                           -- node point) while second SignalGroupID in the 
                           -- next Connection entry represents the 'outbound'
                           -- flow. And use of RestrictionClassID entires
                           -- in the Connect follow this same pattern in pairs.
   hasPushToWalkButton     (5),
                           -- Has a demand input
   audioSupport            (6),
                           -- audio crossing cues present
   rfSignalRequestPresent  (7),
                           -- Supports RF push to walk technologies
   unsignalizedSegmentsPresent  (8)
                           -- The lane path consists of one of more segments
                           -- which are not part of a signal group ID
   -- Bits 9~15 reserved and set to zero
   } (SIZE (16))
 
 
 
-- DE_LaneAttributes-ParkingLane (Desc Name) Record 60
LaneAttributes-Parking ::= BIT STRING { 
    -- With bits as defined:
    -- Parking use details, note that detailed restrictions such as 
    -- allowed hours are sent by way of ITIS codes in the TIM message
    parkingRevocableLane         (0),
                                 -- this lane may be activated or not based
                                 -- on the current SPAT message contents
                                 -- if not asserted, the lane is ALWAYS present
    parallelParkingInUse         (1),
    headInParkingInUse           (2),
    doNotParkZone                (3),
                                 -- used to denote fire hydrants as well
                                 -- short disruptions in a parking zone
    parkingForBusUse             (4),
    parkingForTaxiUse            (5),
    noPublicParkingUse           (6)
                                 -- private parking, as in front of
                                 -- private property
   -- Bits 7~15 reserved and set to zero
   } (SIZE (16))
 
 
 
-- DE_LaneAttributes-Sidewalk (Desc Name) Record 61
LaneAttributes-Sidewalk ::= BIT STRING { 
   -- With bits as defined:
   sidewalk-RevocableLane  (0),
                           -- this lane may be activated or not based
                           -- on the current SPAT message contents
                           -- if not asserted, the lane is ALWAYS present
   bicyleUseAllowed        (1),
                           -- The path allows bicycle traffic, 
                           -- if not set, this mode is prohibited
   isSidewalkFlyOverLane   (2),
                           -- path of lane is not at grade
   walkBikes               (3)
                           -- bike traffic must dismount and walk
   -- Bits 4~15 reserved and set to zero
   } (SIZE (16))
 
 
 
-- DE_LaneAttributes-Striping (Desc Name) Record 62
LaneAttributes-Striping ::= BIT STRING { 
   -- With bits as defined:
    stripToConnectingLanesRevocableLane (0),
       -- this lane may be activated or not based
       -- on the current SPAT message contents
       -- if not asserted, the lane is ALWAYS present
    stripDrawOnLeft                (1),
    stripDrawOnRight               (2),
        -- which side of lane to mark
    stripToConnectingLanesLeft     (3),
    stripToConnectingLanesRight    (4),
    stripToConnectingLanesAhead    (5)
        -- the stripe type should be
        -- presented to the user visually
        -- to reflect stripes in the 
        -- intersection for the type of
        -- movement indicated
   -- Bits 6~15 reserved and set to zero
   } (SIZE (16))
 
 
 
-- DE_LaneAttributes-TrackedVehicle (Desc Name) Record 63
LaneAttributes-TrackedVehicle ::= BIT STRING { 
   -- With bits as defined:
    spec-RevocableLane         (0),
                               -- this lane may be activated or not based
                               -- on the current SPAT message contents
                               -- if not asserted, the lane is ALWAYS present
    spec-commuterRailRoadTrack (1), 
    spec-lightRailRoadTrack    (2),
    spec-heavyRailRoadTrack    (3),
    spec-otherRailType         (4)
   -- Bits 5~15 reserved and set to zero
   } (SIZE (16))
 
 
 
-- DE_LaneAttributes-Vehicle (Desc Name) Record 64
LaneAttributes-Vehicle ::= BIT STRING {  
    -- With bits as defined:
    isVehicleRevocableLane       (0),
                                 -- this lane may be activated or not based
                                 -- on the current SPAT message contents
                                 -- if not asserted, the lane is ALWAYS present
    isVehicleFlyOverLane         (1),
                                 -- path of lane is not at grade
    hovLaneUseOnly               (2),
    restrictedToBusUse           (3),
    restrictedToTaxiUse          (4),
    restrictedFromPublicUse      (5),
    hasIRbeaconCoverage          (6)

   -- Bits 7~15 reserved and set to zero
   } (SIZE (16))
 
 
 
-- DE_LaneConnectionID (Desc Name) Record 65
LaneConnectionID ::= INTEGER (0..255)
 
 
 
-- DE_LaneDirection (Desc Name) Record 66
LaneDirection ::= BIT STRING {
    -- With bits as defined:
    -- Allowed directions of travel in the lane object
    -- All lanes are described from the stop line outwards
    ingressPath                 (0), 
                                -- travel from rear of path to front 
                                -- is allowed
    egressPath                  (1)
                                -- travel from front of path to rear 
                                -- is allowed
    -- Notes:  No Travel, i.e. the lane object type does not support
    --         travel (medians, curbs, etc.) is indicated by not 
    --         asserting any bit value
    --         Bi-Directional Travel (such as a ped crosswalk) is 
    --         indicated by asserting both of the bits
    } (SIZE (2))
 
 
 
-- DE_LaneId (Desc Name) Record 67
LaneID ::= INTEGER (0..255)
   -- the value 0 shall be used when the lane ID is
   -- not available or not known
   -- the value 255 is reserved for future use
 
 
 
-- DE_LaneNumber (Desc Name) Record 68
LaneNumber ::= OCTET STRING (SIZE(1))
 
 
 
-- DE_LaneSharing (Desc Name) Record 69
LaneSharing ::= BIT STRING {
    -- With bits as defined:
    overlappingLaneDescriptionProvided  (0),
    -- Assert when another lane object is present to describe the
    -- path of the overlapping shared lane
    -- this construct is not used for lane objects which simply cross
    multipleLanesTreatedAsOneLane       (1),
    -- Assert if the lane object path and width details represents
    -- multiple lanes within it that are not further described

    -- Various modes and type of traffic whhc may share this lane:
    otherNonMotorizedTrafficTypes       (2), -- horse drawn etc.
    individualMotorizedVehicleTraffic   (3),
    busVehicleTraffic                   (4),  
    taxiVehicleTraffic                  (5),
    pedestriansTraffic                  (6),
    cyclistVehicleTraffic               (7),
    trackedVehicleTraffic               (8),
    pedestrianTraffic                   (9)
    } (SIZE (10))
    -- All zeros would indicate 'not shared' and 'not overlapping'
 
 
 
-- DE_LaneWidth (Desc Name) Record 70
LaneWidth ::= INTEGER (0..32767) -- units of 1 cm
 
 
 
-- DE_Latitude (Desc Name) Record 71
Latitude ::= INTEGER (-900000000..900000001)  
   -- LSB = 1/10 micro degree
   -- Providing a range of plus-minus 90 degrees
 
 
 
-- DE_LayerID (Desc Name) Record 72
LayerID ::= INTEGER (0..100)
 
 
 
-- DE_LayerType (Desc Name) Record 73
LayerType ::= ENUMERATED {
     none, 
     mixedContent, -- two or more of the below types
     generalMapData, 
     intersectionData, 
     curveData, 
     roadwaySectionData, 
     parkingAreaData, 
     sharedLaneData,
     ... 
     }
 
 
 
-- DE_LightbarInUse (Desc Name) Record 74
LightbarInUse ::= ENUMERATED {
     unavailable         (0),  -- Not Equipped or unavailable
     notInUse            (1),  -- none active
     inUse               (2),  
     sirenInUse          (3),   
     yellowCautionLights (4),  
     schooldBusLights    (5),  
     arrowSignsActive    (6),  
     slowMovingVehicle   (7),   
     freqStops           (8),   
     reserved            (9)  -- for future use
     }
 
 
 
-- DE_MAYDAY_Location_quality_code (Desc Name) Record 75
Location-quality ::= ENUMERATED {                        
     loc-qual-bt1m       (0), -- quality better than 1 meter
     loc-qual-bt5m       (1), -- quality better than 5 meters
     loc-qual-bt12m      (2), -- quality better than 12.5 meters
     loc-qual-bt50m      (3), -- quality better than 50 meters
     loc-qual-bt125m     (4), -- quality better than 125 meters
     loc-qual-bt500m     (5), -- quality better than 500 meters
     loc-qual-bt1250m    (6), -- quality better than 1250 meters
     loc-qual-unknown    (7)  -- quality value unknown
     } -- 3 bits, appends with loc-tech to make one octet (0..7)
 
 
 
-- DE_MAYDAY_Location_tech_code (Desc Name) Record 76
Location-tech ::= ENUMERATED {                        
     loc-tech-unknown    (0), -- technology type unknown
     loc-tech-GPS        (1), -- GPS technology only
     loc-tech-DGPS       (2), -- differential GPS (DGPS) technology
     loc-tech-drGPS      (3), -- dead reckoning system w/GPS
     loc-tech-drDGPS     (4), -- dead reckoning system w/DGPS
     loc-tech-dr         (5), -- dead reckoning only
     loc-tech-nav        (6), -- autonomous navigation system on-board
     ...,
     loc-tech-fault      (31) -- feature is not working
     }    -- (0..31) 5 bits, appends with loc-quality to make one octet
 
 
 
-- DE_Longitude (Desc Name) Record 77
Longitude ::= INTEGER (-1799999999..1800000001)  
   -- LSB = 1/10 micro degree
   -- Providing a range of plus-minus 180 degrees
 
 
 
-- DE_MergeDivergeNodeAngle (Desc Name) Record 78
MergeDivergeNodeAngle ::= INTEGER (-180..180) 
   -- In units of 1.5 degrees for north
   -- the value -180 shall be used to represent 
   -- data is not available or unknown
 
 
 
-- DE_MinuteOfTheYear (Desc Name) Record 79
MinuteOfTheYear ::= INTEGER (0..527040) 
   -- the value 527040 shall be used for invalid
 
 
 
-- DE_MinutesDuration (Desc Name) Record 80
MinutesDuration ::= INTEGER (0..32000) -- units of minutes
 
 
 
-- DE_MovementPhaseState (Desc Name) Record 81
MovementPhaseState ::= ENUMERATED {
    -- Note that based on the regions and the operating mode not every 
    -- phase will be used in all transportation modes and that not 
    -- every phase will be used in all transportation modes
  
    unavailable (0), 
      -- This state is used for unknown or error 
    dark (1),   
      -- The signal head is dark (unlit)

   -- Reds
    stop-Then-Proceed (2), 
      -- Often called 'flashing red' in US
      -- Driver Action:                     
      --   Stop vehicle at stop line. 
      --   Do not proceed unless it is safe.
      -- Note that the right to proceed either right or left when 
      -- it is safe may be contained in the lane description to 
      -- handle what is called a 'right on red'
    stop-And-Remain (3),
      -- e.g. called 'red light' in US
      -- Driver Action:                     
      --   Stop vehicle at stop line. 
      --   Do not proceed.                     
      -- Note that the right to proceed either right or left when 
      -- it is safe may be contained in the lane description to 
      -- handle what is called a 'right on red'
   
   -- Greens
    pre-Movement (4), 
      -- Not used in the US, red+yellow partly in EU
      -- Driver Action:                     
      --   Stop vehicle. 
      --   Prepare to proceed (pending green)
      --   (Prepare for transition to green/go)
    permissive-Movement-Allowed (5), 
      -- Often called 'permissive green' in US
      -- Driver Action:                     
      --   Proceed with caution, 
      --   must yield to all conflicting traffic 
      -- Conflicting traffic may be present
      -- in the intersection conflict area
    protected-Movement-Allowed (6), 
      -- Often called 'protected green' in US
      -- Driver Action:                     
      --   Proceed, tossing caution to the wind, 
      --   in indicated (allowed) direction.
   
   -- Yellows / Ambers
   -- The vehicle is not allowed to cross the stop bar if it is possible 
   -- to stop without danger. 
    permissive-clearance (7), 
      -- Often called 'permissive yellow' in US
      -- Driver Action:                     
      --   Prepare to stop.
      --   Proceed if unable to stop,
      --   Clear Intersection.
      -- Conflicting traffic may be present
      -- in the intersection conflict area
    protected-clearance (8),  
      -- Often called 'protected yellow' in US
      -- Driver Action: 
      --   Prepare to stop.
      --   Proceed if unable to stop,
      --   in indicated direction (to connected lane)
      --   Clear Intersection.
                    
    caution-Conflicting-Traffic (9)
      -- Often called 'flashing yellow' in US
      -- Often used for extended periods of time
      -- Driver Action: 
      --   Proceed with caution, 
      -- Conflicting traffic may be present
      -- in the intersection conflict area
    }
    -- The above number assignments are not used with UPER encoding
    -- and are only to be used with DER or implicit encoding
 
 
 
-- DE_MsgCount (Desc Name) Record 82
MsgCount ::= INTEGER (0..127)
 
 
 
-- DE_MsgCRC (Desc Name) Record 83
MsgCRC ::= OCTET STRING (SIZE(2)) -- created with the CRC-CCITT polynomial
 
 
 
-- DE_MultiVehicleResponse (Desc Name) Record 84
MultiVehicleResponse ::= ENUMERATED {
     unavailable   (0), -- Not Equipped or unavailable
     singleVehicle (1),  
     multiVehicle  (2),  
     reserved      (3)  -- for future use
     }
 
 
 
-- DE_MUTCDCode (Desc Name) Record 85
MUTCDCode ::= ENUMERATED {
   none            (0), -- non-MUTCD information 
   regulatory      (1), -- "R" Regulatory signs
   warning         (2), -- "W" warning signs
   maintenance     (3), -- "M" Maintenance and construction 
   motoristService (4), -- Motorist Services
   guide           (5), -- "G" Guide signs
   rec             (6), -- Recreation and Cultural Interest 
   ... -- # LOCAL_CONTENT
   } 
     -- values to 127 reserved for std use
     -- values 128 to 255 reserved for local use
 
 
 
-- DE_NMEA_MsgType (Desc Name) Record 86
NMEA-MsgType ::= INTEGER (0..32767)
 
 
 
-- DE_NMEA_Payload (Desc Name) Record 87
NMEA-Payload ::= OCTET STRING (SIZE(1..1023))
 
 
 
-- DE_NMEA_Revision (Desc Name) Record 88
NMEA-Revision ::= ENUMERATED {
     unknown       (0), 
     reserved      (1),
     rev1          (10),
     rev2          (20),
     rev3          (30),
     rev4          (40),
     rev5          (50),
     ... -- # LOCAL_CONTENT
     } 
     -- values to 127 reserved for std use
     -- values 128 to 255 reserved for local use
 
 
 
-- DE_NodeAttribute (Desc Name) Record 89
NodeAttribute ::= ENUMERATED {
   -- Various values which pertain only to the current node point
   
   -- General Items
   reserved,  
   stopLine,             -- point where a mid-path stop line exists
                         -- See also 'do not block' for segments

   -- Path finish details 
   roundedCapStyleA,      -- Used to control final path rounded end shape
                          -- with edge of curve at final point in a circle
   roundedCapStyleB,      -- Used to control final path rounded end shape
                          -- with edge of curve extending 50% of width past
                          -- final point in a circle
   
   -- Topography Points (items with no concept of a distance along the path)
   mergePoint,           -- Japan merge with 1 or more lanes
   divergePoint,         -- Japan diverge with 1 or more lanes
   downstreamStopLine,   -- Japan style downstream intersection 
                                   -- (a 2nd intersection) stop line
   downstreamStartNode,  -- Japan style downstream intersection 
                                   -- (a 2nd intersection) start node
     
   -- Pedestrian Support Attributes
   closedToTraffic,      -- where a pedestrian may NOT go
                         -- to be used during construction events
   safeIsland,           -- a pedestrian safe stopping point
                         -- also called a traffic island
                         -- This usage described a point feature on a path, 
                         -- other entries can describe a path
   curbPresentAtStepOff, -- the sidewalk to street curb is NOT 
                         -- angled where it meets the edge of the 
                         -- roadway (user must step up/down)
 
   -- Lane geometry details  (see standard for defined shapes)
   hydrantPresent,       -- Or other services access 
   ...
   }
 
 
 
-- DE_NTCIPVehicleclass, (Desc Name) Record 90
NTCIPVehicleclass ::= OCTET STRING (SIZE(1)) 
   -- With bits set as per NTCIP values
   -- Priority Request Vehicle Class Type 
   -- in the upper nibble
   -- Priority Request Vehicle Class Level 
   -- in the lower nibble
 
 
 
-- DE_ObjectCount (Desc Name) Record 91
ObjectCount ::= INTEGER (0..6000) -- a count of objects
 
 
 
-- DE_ObstacleDirection (Desc Name) Record 92
ObstacleDirection ::= Heading -- Use the header DE for this unless it proves different.
 
 
 
-- DE_ObstacleDistance (Desc Name) Record 93
ObstacleDistance ::= INTEGER (0..32767) -- LSB units of meters
 
 
 
-- DE_Offset_B10 (Desc Name) Record 94
Offset-B10 ::= INTEGER (-512..511)
 
 
 
-- DE_Offset_B11 (Desc Name) Record 95
Offset-B11 ::= INTEGER (-1024..1023)
 
 
 
-- DE_Offset_B12 (Desc Name) Record 96
Offset-B12 ::= INTEGER (-2048..2047)
 
 
 
-- DE_Offset_B13 (Desc Name) Record 97
Offset-B13 ::= INTEGER (-4096..4095)
 
 
 
-- DE_Offset_B14 (Desc Name) Record 98
Offset-B14 ::= INTEGER (-8192..8191)
 
 
 
-- DE_Offset_B16 (Desc Name) Record 99
Offset-B16 ::= INTEGER (-32768..32767)
 
 
 
-- DE_Payload (Desc Name) Record 100
Payload ::= OCTET STRING (SIZE(1..64))
 
 
 
-- DE_PayloadData (Desc Name) Record 101
PayloadData ::= OCTET STRING (SIZE(1..2048))
 
 
 
-- DE_PedestrianBicycleDetect (Desc Name) Record 102
PedestrianBicycleDetect ::= BOOLEAN -- 
                 -- true if ANY Pedestrians or Bicyclists are 
                 -- detected crossing the target lane or lanes
 
 
 
-- DE_PositionConfidence (Desc Name) Record 103
PositionConfidence ::= ENUMERATED {
   unavailable (0),  -- B'0000  Not Equipped or unavailable
   a500m   (1), -- B'0001  500m  or about 5 * 10 ^ -3 decimal degrees
   a200m   (2), -- B'0010  200m  or about 2 * 10 ^ -3 decimal degrees
   a100m   (3), -- B'0011  100m  or about 1 * 10 ^ -3 decimal degrees
   a50m    (4), -- B'0100  50m   or about 5 * 10 ^ -4 decimal degrees 
   a20m    (5), -- B'0101  20m   or about 2 * 10 ^ -4 decimal degrees 
   a10m    (6), -- B'0110  10m   or about 1 * 10 ^ -4 decimal degrees 
   a5m     (7), -- B'0111  5m    or about 5 * 10 ^ -5 decimal degrees 
   a2m     (8), -- B'1000  2m    or about 2 * 10 ^ -5 decimal degrees 
   a1m     (9), -- B'1001  1m    or about 1 * 10 ^ -5 decimal degrees 
   a50cm  (10), -- B'1010  0.50m or about 5 * 10 ^ -6 decimal degrees 
   a20cm  (11), -- B'1011  0.20m or about 2 * 10 ^ -6 decimal degrees 
   a10cm  (12), -- B'1100  0.10m or about 1 * 10 ^ -6 decimal degrees 
   a5cm   (13), -- B'1101  0.05m or about 5 * 10 ^ -7 decimal degrees 
   a2cm   (14), -- B'1110  0.02m or about 2 * 10 ^ -7 decimal degrees 
   a1cm   (15)  -- B'1111  0.01m or about 1 * 10 ^ -7 decimal degrees 
   } 
   -- Encoded as a 4 bit value
 
 
 
-- DE_PrioritizationResponseStatus (Desc Name) Record 104
PrioritizationResponseStatus ::= ENUMERATED {
   unknown     (0),
               -- unknown state
   requested   (1),
               -- this prioritization request was detected 
               -- by the traffic controller  
   processing  (2),
               -- checking request 
               -- (request is in queue, others requests are prior)
   watchOtherTraffic (3),
               -- can not give full permission, 
               -- therefore watch for other traffic
   granted     (4),
               -- intervention was successful 
               -- and now prioritization is active
   rejected    (5),
               -- the prioritization or preemption request was 
               -- rejected by the traffic controller
   maxPresence (6)
               -- request has exceeded maxPresence time
   }
 
 
 
-- DE_Priority (Desc Name) Record 105
Priority ::= OCTET STRING (SIZE(1)) 
    -- Follow definition notes on setting these bits
 
 
 
-- DE_ProbeSegmentNumber (Desc Name) Record 106
ProbeSegmentNumber ::= INTEGER (0..32767)  
   -- value determined by local device 
   -- as per standard
 
 
 
-- DE_RainSensor (Desc Name) Record 107
RainSensor ::= ENUMERATED {
     none               (0), 
     lightMist          (1), 
     heavyMist          (2), 
     lightRainOrDrizzle (3),
     rain               (4),
     moderateRain       (5),
     heavyRain          (6),
     heavyDownpour      (7) 
     }
 
 
 
-- DE_RequestedItem (Desc Name) Record 108
RequestedItem ::= ENUMERATED {
   reserved      (0),
   itemA         (1),
        -- consisting of 2 elements: 
        -- lights          ExteriorLights 
        -- lightBar        LightbarInUse 
   
   itemB         (2),
        -- consisting of: 
        -- wipers  a SEQUENCE
   
   itemC         (3),
        -- consisting of: 
        -- brakeStatus  BrakeSystemStatus 

   itemD         (4),
        -- consisting of 2 elements: 
        -- brakePressure   BrakeAppliedPressure   
        -- roadFriction    CoefficientOfFriction   
      
   itemE         (5),
        -- consisting of 4 elements: 
        -- sunData         SunSensor                
        -- rainData        RainSensor                   
        -- airTemp         AmbientAirTemperature     
        -- airPres         AmbientAirPressure     
   
   itemF         (6),
        -- consisting of: 
        -- steering  a SEQUENCE 
    
   itemG         (7),
        -- consisting of: 
        -- accelSets a SEQUENCE 
   
   itemH         (8),
        -- consisting of: 
        -- object a SEQUENCE 
   
   
   itemI         (9),
        -- consisting of: 
        -- fullPos         FullPositionVector       
   
   itemJ         (10),
        -- consisting of: 
        -- position2D      Position2D  

   itemK         (11),
        -- consisting of: 
        -- position3D      Position3D 
 
   itemL         (12),
        -- consisting of 2 elements: 
        -- speedHeadC      SpeedandHeadingConfidence     
        -- speedC          SpeedConfidence  
   
   itemM         (13),
        -- consisting of: 
        -- vehicleData a SEQUENCE   
   
   itemN         (14),
        -- consisting of: 
        -- vehicleIdent   VehicleIdent 
   
   itemO         (15),
        -- consisting of: 
        -- weatherReport a SEQUENCE   
   
   itemP         (16),
        -- consisting of: 
        -- breadcrumbs    VehicleMotionTrail 
   
   itemQ         (17),
        -- consisting of: 
        -- gpsStatus      GPSstatus      
      
   ... -- # LOCAL_CONTENT OPTIONAL,        
   }
   -- values to 127 reserved for std use
   -- values 128 to 255 reserved for local use
 
 
 
-- DE_ResponseType (Desc Name) Record 109
ResponseType ::= ENUMERATED {
   notInUseOrNotEquipped      (0),            
   emergency                  (1),            
   nonEmergency               (2),            
   pursuit                    (3)        
   -- all others Future Use
   } 
   -- values to 127 reserved for std use
   -- values 128 to 255 reserved for local use
 
 
 
-- DE_RestrictionAppliesTo (Desc Name) Record 110
RestrictionAppliesTo ::= ENUMERATED {
    none,              -- applies to nothing
    equippedTransit,   -- buses etc.
    equippedTaxis,
    equippedOther,     -- other vehicle types with
                       -- necessary signal phase state
                       -- reception equipment
    emissionCompliant, -- regional variants with more
                       -- definitive items also exist
    equippedBicycle,
    weightCompliant,
    heightCompliant,
    -- Items dealing with traveler needs
    -- (presumed to be suitably equipped)
    pedestrians,
    slowMovingPersons,
    wheelchairUsers,
    visualDisabilities,
    audioDisabilities,  -- hearing
    otherUnknownDisabilities,
    ...
    }
 
 
 
-- DE_RestrictionClassID (Desc Name) Record 111
RestrictionClassID ::= INTEGER (0..255)
   -- An index value to identify data about classes of users
   -- the value used varies with each intersection's
   -- needs and is defined in the map to the assigned 
   -- classes of supported users.
 
 
 
-- DE_RoadRegulatorID (Desc Name) Record 112
RoadRegulatorID ::= INTEGER (0..65535)
   -- The value zero shall be used for testing only
 
 
 
-- DE_RoadSegmentID (Desc Name) Record 113
RoadSegmentID ::= INTEGER (0..65535)
   -- The values zero to 255 shall be used for testing only
   -- Note that the value assign to an RoadSegment will be
   -- unique within a given regional ID only during its use
 
 
 
-- DE_RoadwayCrownAngle (Desc Name) Record 114
RoadwayCrownAngle ::= INTEGER (-128..127) 
    -- In LSB units of 0.3 degrees of angle
    -- over a range of -38.1 to + 38.1 degrees
    -- The value -128 shall be used for unknown
    -- The value zero shall be used for angles 
    -- which are between -0.15 and +0.15
 
 
 
-- DE_RTCM_ID (Desc Name) Record 115
RTCM-ID ::= INTEGER (0..32767)
 
 
 
-- DE_RTCM_Payload (Desc Name) Record 116
RTCM-Payload ::= OCTET STRING (SIZE(1..1023))
 
 
 
-- DE_RTCM_Revision (Desc Name) Record 117
RTCM-Revision ::= ENUMERATED {
     unknown       (0), 
     reserved      (1),
     rtcmCMR       (2),
     rtcmCMR-Plus  (3),
     rtcmSAPOS     (4),
     rtcmSAPOS-Adv (5),
     rtcmRTCA      (6),
     rtcmRAW       (7),
     rtcmRINEX     (8),
     rtcmSP3       (9),
     rtcmBINEX     (10),
     rtcmRev2-x    (19), -- Used when specific rev is not known
     rtcmRev2-0    (20),
     rtcmRev2-1    (21),
     rtcmRev2-3    (23), -- Std 10402.3
     rtcmRev3-0    (30), 
     rtcmRev3-1    (31), -- Std 10403.1
     ... -- # LOCAL_CONTENT
     } 
     -- values to 127 reserved for std use
     -- values 128 to 255 reserved for local use
 
 
 
-- DE_Scale_B12 (Desc Name) Record 118
Scale-B12 ::= INTEGER (-2048..2047)  -- in steps of 0.05 percent
 
 
 
-- DE_SegmentAttribute (Desc Name) Record 119
SegmentAttribute ::= ENUMERATED {
   -- Various values which can be Enabled and Disabled for a lane segement
   
   -- General Items
   reserved                  ,  
   doNotBlock                ,  -- segment where a vehicle 
                                -- may not come to a stop
   whiteLine                 ,  -- segment where lane crossing not allowed
                                -- such as the final few meters of a lane
   
   -- Porous Lane states, merging, turn outs, parking etc.
   
   mergingLaneLeft           ,  -- indicates porous lanes
   mergingLaneRight          ,
   
   curbOnLeft                ,  -- indicates presence of curbs
   curbOnRight               ,
   
   loadingzoneOnLeft         ,  -- loading or drop off zones
   loadingzoneOnRight        ,
   
   turnOutPointOnLeft        ,  -- opening to adjacent street/alley/road
   turnOutPointOnRight       ,
   
   adjacentParkingOnLeft     , -- side of road parking
   adjacentParkingOnRight    ,
   
   -- Bike Lane Needs
   adjacentBikeLaneOnLeft    , -- presence of marked bike lanes
   adjacentBikeLaneOnRight   ,
   sharedBikeLane            , -- right of way is shared with bikes
                               -- who may occupy entire lane width
   bikeBoxInFront            ,
   
   -- Transit Needs
   transitStopOnLeft         , -- any form of bus/transit loading
                               -- with pull in-out access to lane on left
   transitStopOnRight        , -- any form of bus/transit loading
                               -- with pull in-out access to lane on right
   transitStopInLane         , -- any form of bus/transit loading
                               -- in mid path of the lane
   sharedWithTrackedVehicle  , -- lane is shared with train or trolley 
                               -- not used for crossing tracks
  
     
   -- Pedestrian Support Attributes
   safeIsland                , -- begin/end a safety island in path
   lowCurbsPresent           , -- for ADA support
   rumbleStripPresent        , -- for ADA support
   audibleSignalingPresent   , -- for ADA support
   adaptiveTimingPresent     , -- for ADA support
   rfSignalRequestPresent    , -- Supports RF push to walk technologies
   partialCurbIntrusion      , -- path is blocked by a median or curb 
                               -- but at least 1 meter remains open for use
                               -- and at-grade passage
   
   -- Lane geometry details  (see standard for defined shapes)
   taperToLeft               , -- Used to control final path shape
   taperToRight              , -- Used to control final path shape
   taperToCenterLine         , -- Used to control final path shape

   -- Parking Lane and Curb Attributes
   parallelParking           , -- 
   headInParking             , -- Parking at an angle with the street
   freeParking               , -- no restriction on use of parking
   timeRestrictionsOnParking , -- Parking is not permitted at all times
                               -- typically used when the 'parking' lane 
                               -- becomes a driving lane at times
   costToPark                , -- Used parking has a cost
   midBlockCurbPresent       , -- a protruding curb near lane edge
   unEvenPavementPresent     , -- a disjoint height at lane edge
   ...
   }
 
 
 
-- DE_SignalControlState (Desc Name) Record 120
SignalControlState ::= OCTET STRING (SIZE(1)) 
    -- With bits set as follows:
   
    -- Bit 7 (MSB) Set if the state is currently active
    -- only one active state can exist at a time, and 
    -- this state should be sent first in any sequences
   
    -- Bits 6~4 The preempt or priority value that is 
    -- being described.  
   
    -- Bits 3~0 the state bits, indicating either a 
    -- preemption or a priority use as follows: 
   
    -- If a preemption: to follow the 
    -- preemptState object of NTCIP 1202 v2.19f  
    -- See PreemptState for bit definitions.
   
    -- If a prioirty to follow the 
    -- tspInputStatus object utilized in the 
    -- NYC ASTC2 traffic controller
    -- See PriorityState for bit definitions
 
 
 
-- DE_SignalGroupID (Desc Name) Record 121
SignalGroupID ::= INTEGER (0..255) 
    -- The value 0 shall be used when the ID is
    -- not available or not known
    -- the value 255 is reserved to indicate a 
    -- permanent green movement state
    -- therefore a simple 8 phase signal controller 
    -- device might use 1..9 as its groupIDs
 
 
 
-- DE_SignalReqScheme (Desc Name) Record 122
SignalReqScheme ::= OCTET STRING (SIZE(1)) 
    -- Encoded as follows: 
   -- upper nibble:  Preempt #:  
    -- Bit 7 (MSB) 1 =  Preempt and 0 =  Priority 
    -- Remaining 3 bits: 
    -- Range of 0..7. The values of 1..6 represent 
    -- the respective controller preempt or Priority 
    -- to be activated. The value of 7 represents a 
    -- request for a cabinet flash prempt, 
    -- while the value of 0 is reserved.  
   
   -- lower nibble:  Strategy #:  
    -- Range is 0..15 and is used to specify a desired 
    -- strategy (if available).  
    -- Currently no strategies are defined and this 
    -- should be zero.
 
 
 
-- DE_SignalState (Desc Name) Record 123
SignalState ::= OCTET STRING (SIZE(1)) 
    -- With bits set as follows:
   
    -- Bit 7 (MSB) Set if the state is currently active
    -- only one active state can exist at a time, and 
    -- this state should be sent first in any sequences
   
    -- Bits 6~4 The preempt or priority value that is 
    -- being described.  
   
    -- Bits 3~0 the state bits, indicating either a 
    -- preemption or a priority use as follows: 
   
    -- If a preemption: to follow the 
    -- preemptState object of NTCIP 1202 v2.19f  
    -- See PreemptState for bit definitions.
   
    -- If a prioirty to follow the 
    -- tspInputStatus object utilized in the 
    -- NYC ASTC2 traffic controller
    -- See PriorityState for bit definitions
 
 
 
-- DE_SignPrority (Desc Name) Record 124
SignPrority ::= INTEGER (0..7)
   -- 0 as least, 7 as most
 
 
 
-- DE_SirenInUse (Desc Name) Record 125
SirenInUse ::= ENUMERATED {
     unavailable   (0), -- Not Equipped or unavailable
     notInUse      (1),  
     inUse         (2),  
     reserved      (3)  -- for future use
     }
 
 
 
-- DE_Speed (Desc Name) Record 126
Speed ::= INTEGER (0..8191) -- Units of 0.02 m/s
          -- The value 8191 indicates that 
          -- speed is unavailable
 
 
 
-- DE_SpeedAdvice (Desc Name) Record 127
SpeedAdvice ::= INTEGER (0..500) -- Units of 0.1 m/s
         -- The value 500 indicates that 
         -- speed is unavailable
 
 
 
-- DE_SpeedConfidence (Desc Name) Record 128
SpeedConfidence ::= ENUMERATED {
   unavailable (0), -- B'000  Not Equipped or unavailable
   prec100ms   (1), -- B'001  100  meters / sec
   prec10ms    (2), -- B'010  10   meters / sec
   prec5ms     (3), -- B'011  5    meters / sec
   prec1ms     (4), -- B'100  1    meters / sec
   prec0-1ms   (5), -- B'101  0.1  meters / sec
   prec0-05ms  (6), -- B'110  0.05 meters / sec
   prec0-01ms  (7)  -- B'111  0.01 meters / sec
   } 
   -- Encoded as a 3 bit value
 
 
 
-- DE_SpeedLimitType (Desc Name) Record 129
SpeedLimitType ::= ENUMERATED {
    unknown,                    -- Speed limit type not available
    maxSpeedInSchoolZone,       -- Only sent when the limit is active
    maxSpeedInSchoolZoneWhenChildrenArePresent, -- Sent at any time
    maxSpeedInConstructionZone, -- Used for work zones, incident zones, etc.
                                -- where a reduced speed is present
    vehicleMinSpeed,
    vehicleMaxSpeed,            -- Regulatory speed limit for general traffic
    vehicleNightMaxSpeed,

    truckMinSpeed,
    truckMaxSpeed,
    truckNightMaxSpeed,

    vehiclesWithTrailersMinSpeed,
    vehiclesWithTrailersMaxSpeed,
    vehiclesWithTrailersNightMaxSpeed,
    ...
    }
 
 
 
-- DE_StabilityControlStatus (Desc Name) Record 130
StabilityControlStatus ::= ENUMERATED {
   unavailable (0), -- B'00  Not Equipped with SC
                    -- or SC status is unavailable
   off         (1), -- B'01  Off
   on          (2)  -- B'10  On or active (engaged)
   } 
   -- Encoded as a 2 bit value
 
 
 
-- DE_StationID (Desc Name) Record 131
StationID ::= INTEGER (0..4294967295)
 
 
 
-- DE_J1939-71-Steering Axle Lube Pressure (Desc Name) Record 132
SteeringAxleLubePressure ::= INTEGER (0..255)
 
 
 
-- DE_J1939-71-Steering Axle Temperature (Desc Name) Record 133
SteeringAxleTemperature ::= INTEGER (0..255)
 
 
 
-- DE_SteeringWheelAngle (Desc Name) Record 134
SteeringWheelAngle ::= OCTET STRING (SIZE(1)) 
    -- LSB units of 1.5 degrees.  
    -- a range of -189 to +189 degrees
    -- 0x01 = 00 = +1.5 deg
    -- 0x81 = -126 = -189 deg and beyond
    -- 0x7E = +126 = +189 deg and beyond
    -- 0x7F = +127 to be used for unavailable
 
 
 
-- DE_SteeringWheelAngleConfidence (Desc Name) Record 135
SteeringWheelAngleConfidence ::= ENUMERATED {
   unavailable (0), -- B'00  Not Equipped with Wheel angle
                    -- or Wheel angle status is unavailable
   prec2deg    (1), -- B'01  2 degrees
   prec1deg    (2), -- B'10  1 degree
   prec0-02deg (3)  -- B'11  0.02 degrees
   } 
   -- Encoded as a 2 bit value
 
 
 
-- DE_SteeringWheelAngleRateOfChange (Desc Name) Record 136
SteeringWheelAngleRateOfChange ::= INTEGER (-127..127) 
   -- LSB is 3 degrees per second
 
 
 
-- DE_SunSensor (Desc Name) Record 137
SunSensor ::= INTEGER (0..1000) 
   -- units of watts / m2
 
 
 
-- DE_TemporaryID (Desc Name) Record 138
TemporaryID ::= OCTET STRING (SIZE(4)) -- a 4 byte string array
 
 
 
-- DE_TerminationDistance (Desc Name) Record 139
TermDistance ::= INTEGER (1..30000)   -- units in meters
 
 
 
-- DE_TerminationTime (Desc Name) Record 140
TermTime ::= INTEGER (1..1800) -- units of sec
 
 
 
-- DE_ThrottleConfidence (Desc Name) Record 141
ThrottleConfidence ::= ENUMERATED {
   unavailable     (0), -- B'00  Not Equipped or unavailable
   prec10percent   (1), -- B'01  10  percent Confidence level
   prec1percent    (2), -- B'10  1   percent Confidence level
   prec0-5percent  (3)  -- B'11  0.5 percent Confidence level
   } 
   -- Encoded as a 2 bit value
 
 
 
-- DE_ThrottlePosition (Desc Name) Record 142
ThrottlePosition ::= INTEGER (0..200) -- LSB units are 0.5 percent
 
 
 
-- DE_TimeConfidence (Desc Name) Record 143
TimeConfidence ::= ENUMERATED {
   unavailable              (0), -- Not Equipped or unavailable
   time-100-000             (1), -- Better then  100 Seconds
   time-050-000             (2), -- Better then  50 Seconds
   time-020-000             (3), -- Better then  20 Seconds
   time-010-000             (4), -- Better then  10 Seconds
   time-002-000             (5), -- Better then  2 Seconds
   time-001-000             (6), -- Better then  1 Second
   time-000-500             (7), -- Better then  0.5 Seconds
   time-000-200             (8), -- Better then  0.2 Seconds
   time-000-100             (9), -- Better then  0.1 Seconds
   time-000-050            (10), -- Better then  0.05 Seconds
   time-000-020            (11), -- Better then  0.02 Seconds
   time-000-010            (12), -- Better then  0.01 Seconds
   time-000-005            (13), -- Better then  0.005 Seconds
   time-000-002            (14), -- Better then  0.002 Seconds
   time-000-001            (15), -- Better then  0.001 Seconds
                                 -- Better then one milisecond
   time-000-000-5          (16), -- Better then  0.000,5 Seconds
   time-000-000-2          (17), -- Better then  0.000,2 Seconds
   time-000-000-1          (18), -- Better then  0.000,1 Seconds
   time-000-000-05         (19), -- Better then  0.000,05 Seconds
   time-000-000-02         (20), -- Better then  0.000,02 Seconds
   time-000-000-01         (21), -- Better then  0.000,01 Seconds
   time-000-000-005        (22), -- Better then  0.000,005 Seconds
   time-000-000-002        (23), -- Better then  0.000,002 Seconds
   time-000-000-001        (24), -- Better then  0.000,001 Seconds 
                                 -- Better then one micro second
   time-000-000-000-5      (25), -- Better then  0.000,000,5 Seconds
   time-000-000-000-2      (26), -- Better then  0.000,000,2 Seconds
   time-000-000-000-1      (27), -- Better then  0.000,000,1 Seconds
   time-000-000-000-05     (28), -- Better then  0.000,000,05 Seconds
   time-000-000-000-02     (29), -- Better then  0.000,000,02 Seconds
   time-000-000-000-01     (30), -- Better then  0.000,000,01 Seconds
   time-000-000-000-005    (31), -- Better then  0.000,000,005 Seconds
   time-000-000-000-002    (32), -- Better then  0.000,000,002 Seconds
   time-000-000-000-001    (33), -- Better then  0.000,000,001 Seconds
                                 -- Better then one nano second
   time-000-000-000-000-5  (34), -- Better then  0.000,000,000,5 Seconds
   time-000-000-000-000-2  (35), -- Better then  0.000,000,000,2 Seconds
   time-000-000-000-000-1  (36), -- Better then  0.000,000,000,1 Seconds
   time-000-000-000-000-05 (37), -- Better then  0.000,000,000,05 Seconds
   time-000-000-000-000-02 (38), -- Better then  0.000,000,000,02 Seconds
   time-000-000-000-000-01 (39)  -- Better then  0.000,000,000,01 Seconds 
   }
 
 
 
-- DE_TimeIntervalConfidence (Desc Name) Record 144
TimeIntervalConfidence ::= INTEGER (0..15)   
   -- Value   Probability
   --   0         21%
   --   1         36%
   --   2         47%
   --   3         56%
   --   4         62%
   --   5         68%
   --   6         73%
   --   7         77%
   --   8         81%
   --   9         85%
   --   10        88%
   --   11        91%
   --   12        94%
   --   13        96%
   --   14        98%
   --   15        100%
 
 
 
-- DE_TimeMark (Desc Name) Record 145
TimeMark ::= INTEGER (0..36002)
   -- Tenths of a second in the current or next hour
   -- In units of 1/10th second from UTC time
   -- A range of 0~36000 covers one hour
   -- The values 35991..36000 are used when a leap second occurs
   -- The value 36001 is used to indicate time >3600 seconds
   -- 36002 is to be used when value undefined or unknown
   -- Note that this is NOT expressed in GPS time
   -- or in local time
 
 
 
-- DE_J1939-71-Tire Leakage Rate (Desc Name) Record 146
TireLeakageRate ::= INTEGER (0..65535)
 
 
 
-- DE_J1939-71-Tire Location (Desc Name) Record 147
TireLocation ::= INTEGER (0..255)
 
 
 
-- DE_J1939-71-Tire Pressure (Desc Name) Record 148
TirePressure ::= INTEGER (0..1000)
 
 
 
-- DE_J1939-71-Tire Pressure Threshold Detection (Desc Name) Record 149
TirePressureThresholdDetection ::= ENUMERATED {
   noData                (0),  -- B'000'
   overPressure          (1),  -- B'001' 
   noWarningPressure     (2),  -- B'010'
   underPressure         (3),  -- B'011'
   extremeUnderPressure  (4),  -- B'100'
   undefined             (5),  -- B'101'
   errorIndicator        (6),  -- B'110'
   notAvailable          (7),  -- B'111'
   ... -- # LOCAL_CONTENT
   }
 
 
 
-- DE_J1939-71-Tire Temp (Desc Name) Record 150
TireTemp ::= INTEGER (0..65535)
 
 
 
-- DE_TractionControlState (Desc Name) Record 151
TractionControlState ::= ENUMERATED {
   unavailable (0), -- B'00  Not Equipped with tracton control 
                    -- or tracton control status is unavailable
   off         (1), -- B'01  tracton control is Off
   on          (2), -- B'10  tracton control is On (but not Engaged)
   engaged     (3)  -- B'11  tracton control is Engaged
   } 
   -- Encoded as a 2 bit value
 
 
 
-- DE_J1939-71-Trailer Weight (Desc Name) Record 152
TrailerWeight ::= INTEGER (0..65535)
 
 
 
-- DE_TransitStatus (Desc Name) Record 153
TransitStatus ::= BIT STRING {
    none        (0), -- nothing is active
    anADAuse    (1), -- an ADA access is in progress (wheelchairs, kneling, etc.)
    aBikeLoad   (2), -- loading of a bicyle is in progress
    doorOpen    (3), -- a vehicle door is open for passenger access
    occM        (4),
    occL        (5)
    -- bits four and five are used to relate the 
    -- the relative occupancy of the vehicle, with
    -- 00  as least full and 11 indicating a 
    -- close-to or full conditon
    } (SIZE(6))
 
 
 
-- DE_TransmissionState (Desc Name) Record 154
TransmissionState ::= ENUMERATED {
   neutral         (0), -- Neutral, speed relative to the vehicle alignment
   park            (1), -- Park, speed relative the to vehicle alignment
   forwardGears    (2), -- Forward gears, speed relative the to vehicle alignment
   reverseGears    (3), -- Reverse gears, speed relative the to vehicle alignment 
   reserved1       (4),      
   reserved2       (5),      
   reserved3       (6),      
   unavailable     (7), -- not-equipped or unavailable value,
                        -- speed relative to the vehicle alignment

   ... -- # LOCAL_CONTENT
   }
 
 
 
-- DE_TravelerInfoType (Desc Name) Record 155
TravelerInfoType ::= ENUMERATED {
     unknown            (0), 
     advisory           (1),
     roadSignage        (2), 
     commercialSignage  (3),
     ... -- # LOCAL_CONTENT
     } 
     -- values to 127 reserved for std use
     -- values 128 to 255 reserved for local use
 
 
 
-- DE_TransmitInterval (Desc Name) Record 156
TxTime ::= INTEGER (1..20)   -- units of seconds
 
 
 
-- DE_UniqueMSG_ID (Desc Name) Record 157
UniqueMSGID ::= OCTET STRING (SIZE(9))
 
 
 
-- DE_UPER_Blob (Desc Name) Record 158
UPER-Blob ::= OCTET STRING (SIZE(10..2000)) 
    -- Final size range may be further 
    -- limited by the transport layer used
 
 
 
-- DE_URL_Base (Desc Name) Record 159
URL-Base ::= IA5String (SIZE(1..45))
 
 
 
-- DE_URL_Link (Desc Name) Record 160
URL-Link ::= IA5String (SIZE(1..255))
 
 
 
-- DE_URL_Short (Desc Name) Record 161
URL-Short ::= IA5String (SIZE(1..15))
 
 
 
-- DE_VehicleHeight (Desc Name) Record 162
VehicleHeight ::= INTEGER (0..127) 
    -- the height of the vehicle
    -- LSB units of 5 cm, range to 6.35 meters
 
 
 
-- DE_VehicleLength (Desc Name) Record 163
VehicleLength ::= INTEGER (0..16383) -- LSB units are 1 cm
 
 
 
-- DE_VehicleMass (Desc Name) Record 164
VehicleMass ::= INTEGER (1..127) -- mass with an LSB of 50 Kg
 
 
 
-- DE_VehicleRequestStatus (Desc Name) Record 165
VehicleRequestStatus ::= OCTET STRING (SIZE(1)) 
  -- With bits set as follows: 
  -- Bit 7 (MSB)  Brakes-on, see notes for use 
  -- Bit 6 Emergency Use or operation 
  -- Bit 5 Lights in use (see also the light bar element)
  -- Bits 5~0
  -- when a priority, map the values of 
  -- LightbarInUse to the lower 4 bits 
  -- and set the 5th bit to zero
  -- when a preemption, map the values of 
  -- TransistStatus to the lower 5 bits
 
 
 
-- DE_VehicleStatusDeviceTypeTag (Desc Name) Record 166
VehicleStatusDeviceTypeTag ::= ENUMERATED {
   unknown            (0),
   lights             (1),  -- Exterior Lights
   wipers             (2),  -- Wipers
   brakes             (3),  -- Brake Applied                
   stab               (4),  -- Stability Control        
   trac               (5),  -- Traction Control        
   abs                (6),  -- Anti-Lock Brakes        
   sunS               (7),  -- Sun Sensor        
   rainS              (8),  -- Rain Sensor        
   airTemp            (9),  -- Air Temperature    
   steering           (10),
   vertAccelThres     (11), -- Wheel that Exceeded the
   vertAccel          (12), -- Vertical g Force Value  
   hozAccelLong       (13), -- Longitudinal Acceleration        
   hozAccelLat        (14), -- Lateral Acceleration        
   hozAccelCon        (15), -- Acceleration Confidence 
   accel4way          (16),
   confidenceSet      (17),
   obDist             (18), -- Obstacle Distance        
   obDirect           (19), -- Obstacle Direction        
   yaw                (20), -- Yaw Rate        
   yawRateCon         (21), -- Yaw Rate Confidence
   dateTime           (22), -- complete time
   fullPos            (23), -- complete set of time and
                            -- position, speed, heading
   position2D         (24), -- lat, long
   position3D         (25), -- lat, long, elevation
   vehicle            (26), -- height, mass, type
   speedHeadC         (27), 
   speedC             (28),
   
   ... -- # LOCAL_CONTENT
   }
   -- values to 127 reserved for std use
   -- values 128 to 255 reserved for local use
 
 
 
-- DE_VehicleType (Desc Name) Record 167
VehicleType ::= ENUMERATED {
   none                 (0),  -- Not Equipped, Not known or unavailable
   unknown              (1),  -- Does not fit any other category    
   special              (2),  -- Special use    
   moto                 (3),  -- Motorcycle    
   car                  (4),  -- Passenger car    
   carOther             (5),  -- Four tire single units    
   bus                  (6),  -- Buses    
   axleCnt2             (7),  -- Two axle, six tire single units    
   axleCnt3             (8),  -- Three axle, single units    
   axleCnt4             (9),  -- Four or more axle, single unit    
   axleCnt4Trailer      (10), -- Four or less axle, single trailer    
   axleCnt5Trailer      (11), -- Five or less axle, single trailer    
   axleCnt6Trailer      (12), -- Six or more axle, single trailer    
   axleCnt5MultiTrailer (13), -- Five or less axle, multi-trailer    
   axleCnt6MultiTrailer (14), -- Six axle, multi-trailer    
   axleCnt7MultiTrailer (15),  -- Seven or more axle, multi-trailer    
   ... -- # LOCAL_CONTENT
   } 
   -- values to 127 reserved for std use
   -- values 128 to 255 reserved for local use
 
 
 
-- DE_VehicleWidth (Desc Name) Record 168
VehicleWidth ::= INTEGER (0..1023) -- LSB units are 1 cm
 
 
 
-- DE_Velocity (Desc Name) Record 169
Velocity ::= INTEGER (0..8191) -- Units of 0.02 m/s
          -- The value 8191 indicates that 
          -- velocity is unavailable
 
 
 
-- DE_VerticalAcceleration (Desc Name) Record 170
VerticalAcceleration ::= INTEGER (-127..127) 
   -- LSB units of 0.02 G steps over 
   -- a range +1.54 to -3.4G 
   -- and offset by 50  Value 50 = 0g, Value 0 = -1G
   -- value +127 = 1.54G, 
   -- value -120 = -3.4G
   -- value -121 for ranges -3.4 to -4.4G
   -- value -122 for ranges -4.4 to -5.4G
   -- value -123 for ranges -5.4 to -6.4G
   -- value -124 for ranges -6.4 to -7.4G
   -- value -125 for ranges -7.4 to -8.4G
   -- value -126 for ranges larger than -8.4G
   -- value -127 for unavailable data
 
 
 
-- DE_VerticalAccelerationThreshold (Desc Name) Record 171
VerticalAccelerationThreshold ::= BIT STRING {
   allOff      (0), -- B'0000  The condition All Off or not equipped
   leftFront   (1), -- B'0001  Left Front Event
   leftRear    (2), -- B'0010  Left Rear Event
   rightFront  (4), -- B'0100  Right Front Event
   rightRear   (8)  -- B'1000  Right Rear Event
   } -- to fit in 4 bits
 
 
 
-- DE_VINstring, (Desc Name) Record 172
VINstring ::= OCTET STRING (SIZE(1..17)) 
   -- A legal VIN or a shorter value 
   -- to provide an ident of the vehicle
   -- If a VIN is sent, then IA5 encoding 
   -- shall be used
 
 
 
-- DE_WaitOnStopline (Desc Name) Record 173
WaitOnStopline ::= BOOLEAN -- 
         -- True or False
         -- If "true", the vehicles on this specific connecting 
         -- maneuver have to stop on the stop-line
         -- and not to enter the collision area
 
 
 
-- DE_J1939-71-Wheel End Elect. Fault (Desc Name) Record 174
WheelEndElectFault ::= BIT STRING {
   bitOne      (1),
   bitTwo      (2),
   bitThree    (3),
   bitFour     (4)
   }
 
 
 
-- DE_J1939-71-Wheel Sensor Status (Desc Name) Record 175
WheelSensorStatus ::= ENUMERATED {
     off           (0), 
     on            (1),
     notDefined    (2), 
     notSupoprted  (3)
     }
 
 
 
-- DE_WiperRate (Desc Name) Record 176
WiperRate ::= INTEGER (0..127) -- units of sweeps per minute
 
 
 
-- DE_WiperStatusFront (Desc Name) Record 177
WiperStatusFront ::= ENUMERATED {
     unavailable         (0), -- Not Equipped with wiper status
                              -- or wiper status is unavailable
     off                 (1),  
     intermittent        (2), 
     low                 (3),
     high                (4),
     washerInUse       (126), -- washing solution being used
     automaticPresent  (127), -- Auto wiper equipped
     ... -- # LOCAL_CONTENT
     }
 
 
 
-- DE_WiperStatusRear (Desc Name) Record 178
WiperStatusRear ::= ENUMERATED {
     unavailable         (0), -- Not Equipped with wiper status
                              -- or wiper status is unavailable
     off                 (1),  
     intermittent        (2), 
     low                 (3),
     high                (4),
     washerInUse       (126), -- washing solution being used
     automaticPresent  (127), -- Auto wipper equipped
     ... -- # LOCAL_CONTENT
     }
 
 
 
-- DE_YawRate (Desc Name) Record 179
YawRate ::= INTEGER (-32767..32767) 
   -- LSB units of 0.01 degrees per second (signed)
 
 
 
-- DE_YawRateConfidence (Desc Name) Record 180
YawRateConfidence ::= ENUMERATED {
   unavailable    (0), -- B'000  Not Equipped with yaw rate status
                       -- or yaw rate status is unavailable
   degSec-100-00  (1), -- B'001  100  deg/sec
   degSec-010-00  (2), -- B'010  10   deg/sec
   degSec-005-00  (3), -- B'011  5    deg/sec
   degSec-001-00  (4), -- B'100  1    deg/sec
   degSec-000-10  (5), -- B'101  0.1  deg/sec
   degSec-000-05  (6), -- B'110  0.05 deg/sec
   degSec-000-01  (7)  -- B'111  0.01 deg/sec
   }  
   -- Encoded as a 3 bit value
 
 
 
-- DE_ZoneLength (Desc Name) Record 181
ZoneLength ::= INTEGER (0..10000)
    -- Unit = 1 meter, 0 = unknown, 
    -- The value 10000 to be used for Distances >=10000 m
    -- (e.g. from known point to another point along a 
    -- known path, often against traffic flow direction 
    -- when used for measuring queues)
 
 


-- Unable to find the file: DSRCstubs.txt
-- Which would be be inserted at this point if present.


END 
-- end of the DSRC module.
 
 
 
-- -_-_-_-_-_-_-_-_-_-_-_-_-_-_-_-_-_-_-_-_-_-_-_-_-_-_-_-_
-- 
-- Start of External Data entries...
-- Grouped into sets of modules
-- -_-_-_-_-_-_-_-_-_-_-_-_-_-_-_-_-_-_-_-_-_-_-_-_-_-_-_-_
-- 
-- ^-^-^-^-^-^-^-^-^-^-^-^-^-^-^-^-^-^-^-^-^-^-^-^-^-^-^-^-
-- 
-- Begin module: EU
-- 
-- ^-^-^-^-^-^-^-^-^-^-^-^-^-^-^-^-^-^-^-^-^-^-^-^-^-^-^-^-
EU DEFINITIONS AUTOMATIC TAGS::= BEGIN 
 


-- DF_Altitude_EU (Desc Name) Record 1
-- From source: AMENDMENT Regional Data J2735 (EU)
Altitude ::=  SEQUENCE {
   value        AltitudeValue,
   confidence   AltitudeConfidence
   }

-- DE_AltitudeConfidence_EU (Desc Name) Record 2
-- From source: AMENDMENT Regional Data J2735 (EU)
AltitudeConfidence ::= ENUMERATED {
   alt-000-01,  -- accuracy within    0.01 meter
   alt-000-02,  -- accuracy within    0.02 meter
   alt-000-05,  -- accuracy within    0.05 meter
   alt-000-10,  -- accuracy within    0.10 meter
   alt-000-20,  -- accuracy within    0.20 meter
   alt-000-50,  -- accuracy within    0.50 meter
   alt-001-00,  -- accuracy within    1.00 meter
   alt-002-00,  -- accuracy within    2.00 meter
   alt-005-00,  -- accuracy within    5.00 meter
   alt-010-00,  -- accuracy within   10.00 meter
   alt-020-00,  -- accuracy within   20.00 meter
   alt-050-00,  -- accuracy within   50.00 meter
   alt-100-00,  -- accuracy within  100.00 meter
   alt-200-00,  -- accuracy within  200.00 meter
   outOfRange,  -- accuracy exceeds 200.00 meters
   unavailable  -- unavailable
}

-- DE_AltitudeValue_EU (Desc Name) Record 3
-- From source: AMENDMENT Regional Data J2735 (EU)
AltitudeValue ::= INTEGER (-100000..800001)  -- units of  0.01 meter 
   -- Where: 
   -- seaLevel(0), 
   -- oneCentimeter(1), 
   -- unavailable(800001)

-- DE_EmissionType_EU (Desc Name) Record 10
-- From source: AMENDMENT Regional Data J2735 (EU)
EmissionType ::= ENUMERATED {
     typeA,  -- check for proper restrictions
     typeB,  -- 
     typeC,  -- 
     typeD,  -- 
     typeE,  -- 
     ... -- # LOCAL_CONTENT
     }

-- DF_PrioritizationResponse_EU (Desc Name) Record 34
-- From source: AMENDMENT Regional Data J2735 (EU)
PrioritizationResponse ::=  SEQUENCE {
   stationID      DSRC.StationID,
                  -- Id of requesting vehicle
                  -- Note that the stationID has to remain unchanged 
                  -- during the whole prioritisation process
   priorState     DSRC.PrioritizationResponseStatus,
                  -- State of prioritization request
   signalGroup    DSRC.SignalGroupID,
                  -- id of prioritized LaneSet, which will 
                  -- be given free way 
   ... -- # LOCAL_CONTENT
   }

-- DF_PrioritizationResponseList_EU (Desc Name) Record 35
-- From source: AMENDMENT Regional Data J2735 (EU)
PrioritizationResponseList ::=  SEQUENCE SIZE(1..10) OF PrioritizationResponse

-- DF_Reg-ConnectionManeuverAssist_EU (Desc Name) Record 38
-- From source: AMENDMENT Regional Data J2735 (EU)
EU-Reg-ConnectionManeuverAssist ::=  SEQUENCE {
    vehicleToLanePositions  VehicleToLanePositionList,
    rsuDistanceFromAnchor   DSRC.NodeOffsetPoint OPTIONAL
}

-- DF_REG_IntersectionState_EU (Desc Name) Record 42
-- From source: AMENDMENT Regional Data J2735 (EU)
EU-Reg-IntersectionState ::=  SEQUENCE { 
   activePrioritizations PrioritizationResponseList OPTIONAL,
   ... }

-- DF_REG_MapData_Base_EU   NEW (Desc Name) Record 48
-- From source: AMENDMENT Regional Data J2735 (EU)
EU-Reg-MapData ::=  SEQUENCE { 
   signalHeadLocations   SignalHeadLocationList OPTIONAL,
   ... 
   }

-- DF_REG_Position3D_EU (Desc Name) Record 57
-- From source: AMENDMENT Regional Data J2735 (EU)
EU-Reg-Position3D ::=  SEQUENCE {
   altitude    Altitude, 
   ...
   }

-- DF_REG_RestrictionUserType_EU (Desc Name) Record 58
-- From source: AMENDMENT Regional Data J2735 (EU)
EU-Reg-RestrictionUserType ::=  SEQUENCE {
   emission   EmissionType OPTIONAL,
   ...
   }

-- DF_SignalHeadLocation_EU    NEW (Desc Name) Record 66
-- From source: AMENDMENT Regional Data J2735 (EU)
SignalHeadLocation ::=  SEQUENCE {
   node             DSRC.NodeOffsetPoint, -- the location
   signalGroupID    DSRC.SignalGroupID,   
   ...
}

-- DF_SignalHeadLocationList_EU   NEW (Desc Name) Record 67
-- From source: AMENDMENT Regional Data J2735 (EU)
SignalHeadLocationList ::=  SEQUENCE (SIZE(1..20)) OF  SignalHeadLocation

-- DF_VehicleToLanePosition_EU (Desc Name) Record 73
-- From source: AMENDMENT Regional Data J2735 (EU)
VehicleToLanePosition ::=  SEQUENCE {
    stationID   DSRC.StationID, 
    laneID      DSRC.LaneID,
    ... -- # LOCAL_CONTENT
    }

-- DF_VehicleToLanePositionList_EU (Desc Name) Record 74
-- From source: AMENDMENT Regional Data J2735 (EU)
VehicleToLanePositionList ::=  SEQUENCE SIZE(1..5) OF VehicleToLanePosition


-- Unable to find the file: EUstubs.txt
-- Which would be be inserted at this point if present.


 
END
-- End of the EU module.
 
-- ^-^-^-^-^-^-^-^-^-^-^-^-^-^-^-^-^-^-^-^-^-^-^-^-^-^-^-^-
-- 
-- Begin module: JPN
-- 
-- ^-^-^-^-^-^-^-^-^-^-^-^-^-^-^-^-^-^-^-^-^-^-^-^-^-^-^-^-
JPN DEFINITIONS AUTOMATIC TAGS::= BEGIN 
 


-- DE_Angle_JPN (Desc Name) Record 4
-- From source: AMENDMENT Regional Data J2735 (JPN)
JPN-Angle ::= INTEGER (0..239)
   -- Unsigned units of 1.5 degree, in 1 byte
   -- the true north is 0, positive is clockwise
   -- the values 240 to 254 shall not be sent
   -- the value 255 (0xFF) indicates an invalid value

-- DE_Day_JPN (Desc Name) Record 5
-- From source: AMENDMENT Regional Data J2735 (JPN)
Day ::= INTEGER (0..255) 
   -- BCD coding of Day of Month, in 1 byte
   -- values with nibble values between 1010 and 1111 shall not be sent
   -- except that the value xxx (0xFF shall indicate an invalid value

-- DE_DayOfWeek_JPN (Desc Name) Record 6
-- From source: AMENDMENT Regional Data J2735 (JPN)
DayOfWeek ::= ENUMERATED {
    unknown   (0),
    monday    (1),
    tuesday   (2),
    wednesday (3),
    thursday  (4),
    friday    (5),
    saturday  (6),
    sunday    (7)
    }
   -- Encoding as per above, in 3 bits
   -- the value 0x00 shall indicate an invalid value

-- DE_DegreesLat_JPN (Desc Name) Record 7
-- From source: AMENDMENT Regional Data J2735 (JPN)
DegreesLat ::= INTEGER (-90..90)
   -- Signed units of degrees, in 1 byte
   -- the values  +91 to +126 shall not be sent
   -- the values -128 to  -91 shall not be sent
   -- the value 127 (0x7F) shall indicate an invalid value

-- DE_DegreesLong_JPN (Desc Name) Record 8
-- From source: AMENDMENT Regional Data J2735 (JPN)
DegreesLong ::= INTEGER (-180..180) 
   -- Signed units of degrees, in 2 bytes
   -- the values +181 to +32766 shall not be sent
   -- the values -181 to -32768 shall not be sent
   -- the value 32767 (0x7FFF shall indicate an invalid value

-- DE_Elevation_JPN (Desc Name) Record 9
-- From source: AMENDMENT Regional Data J2735 (JPN)
JPN-Elevation ::= INTEGER (-32768..32767)  
  -- Signed units of 0.1m (10cm), in 2 bytes
  -- the value 32767 (0x7FFF) shall indicate an invalid value

-- DE_Holiday_JPN (Desc Name) Record 16
-- From source: AMENDMENT Regional Data J2735 (JPN)
Holiday ::= ENUMERATED {
    weekday  (0),
    holiday  (1)
    }
   -- Encoding as per above, in 1 bit

-- DE_Hour_JPN (Desc Name) Record 17
-- From source: AMENDMENT Regional Data J2735 (JPN)
Hour ::= INTEGER (0..255) 
   -- BCD coding of Hour of a Day, in 1 byte
   -- values above upper nibble 0010 and lower nibble 0100 shall not be sent
   -- values with lower nibble values between 1010 and 1111 shall not be sent
   -- except that the value 255 (0xFF) shall indicate an invalid value

-- DE_LatitudeDMS (Desc Name) Record 22
-- From source: AMENDMENT Regional Data J2735 (JPN)
LatitudeDMS ::= INTEGER (-32400000.. 32400000) 
   -- Signed units of 0.01 seconds of a minute of a degree of Latitude
   -- Providing a range of plus-minus 90 degrees
   -- in a 4 byte value when implicit or in BER forms
   -- the value 0x7FFF FFFF shall indicate an invalid value

-- DF_LatitudeDMS2 (Desc Name) Record 23
-- From source: AMENDMENT Regional Data J2735 (JPN)
LatitudeDMS2 ::=  SEQUENCE {
   d  DegreesLat,    -- units of degrees
   m  MinutesAngle,  -- units of minutes
   s  SecondsAngle   -- units of 1/100th seconds
   } -- total size of 4 bytes (32 bits) when implicit encoding is used

-- DE_LongitudeDMS (Desc Name) Record 24
-- From source: AMENDMENT Regional Data J2735 (JPN)
LongitudeDMS ::= INTEGER (-64800000.. 64800000) 
   -- Signed units of 0.01 seconds of a minute of a degree of Longitude
   -- Providing a range of plus-minus 180 degrees
   -- in a 4 byte value when implicit or in BER forms
   -- the value 0x7FFF FFFF shall indicate an invalid value

-- DF_LongitudeDMS2 (Desc Name) Record 25
-- From source: AMENDMENT Regional Data J2735 (JPN)
LongitudeDMS2 ::=  SEQUENCE {
   d  DegreesLong,   -- units of degrees
   m  MinutesAngle,  -- units of minutes
   s  SecondsAngle   -- units of 1/100th seconds
   } -- total size of 5 bytes (40 bits) when implicit encoding is used

-- DE_MaxTimetoChange (Desc Name) Record 26
-- From source: AMENDMENT Regional Data J2735 (JPN)
MaxTimetoChange ::= INTEGER (0..2402)
   -- Unsigned units of 0.1 seconds, in 2 bytes
   -- the value 2401 shall indicate 'forever'
   -- the values 2402 to 65534 shall not be sent
   -- the value 65535 (0xFFFF) shall indicate an invalid value

-- DE_MinTimetoChange (Desc Name) Record 27
-- From source: AMENDMENT Regional Data J2735 (JPN)
MinTimetoChange ::= INTEGER (0..2402)
   -- Unsigned units of 0.1 seconds, in 2 bytes
   -- the value 2401 shall indicate 'forever'
   -- the values 2402 to 32766 shall not be sent
   -- the value 32767(0x7FFF) shall indicate an invalid value
   -- Note that:
   -- The MSB is used as a flag and set to one to
   -- indicate that the value does not count down.
   -- Under this condition the movement phase may end
   -- immediately if certain condition are meet.

-- DE_Minute_JPN (Desc Name) Record 28
-- From source: AMENDMENT Regional Data J2735 (JPN)
Minute ::= INTEGER (0..255) 
   -- BCD coding of Minute of an Hour, in 1 byte
   -- values above a combined BCD value of 59 (>59)
   -- (i.e. 0110 0000) shall not be sent
   -- except that value 255 (0xFF) shall indicate an invalid value

-- DE_MinutesAngle_JPN (Desc Name) Record 29
-- From source: AMENDMENT Regional Data J2735 (JPN)
MinutesAngle ::= INTEGER (0..59)   
   -- Unsigned units of minutes of an angle, in 1 byte
   -- values above 59 shall not be sent
   -- except that value 255 (0xFF) shall indicate an invalid value

-- DE_Month_JPN (Desc Name) Record 30
-- From source: AMENDMENT Regional Data J2735 (JPN)
Month ::= INTEGER (1..255) 
   -- BCD coding of Month of a year, in 1 byte
   -- values above a combined BCD value of 12 (>12)
   -- (i.e. 0001 0011) shall not be sent
   -- except that value 255 (0xFF) shall indicate an invalid value

-- DE_MsgCount_JPN (Desc Name) Record 31
-- From source: AMENDMENT Regional Data J2735 (JPN)
JPN-MsgCount ::= INTEGER (0..255)
   -- a count value which is incremented with each use
   -- the next value after 255 shall be one
   -- value 0 (0x00) shall indicate that MsgCount is not available

-- DF_Node_LLdms_48b (Desc Name) Record 32
-- From source: AMENDMENT Regional Data J2735 (JPN)
Node-LLdms-48b ::=  SEQUENCE {
   lon  LongitudeDMS,
   lat  LatitudeDMS
   }

-- DF_Node_LLdms_80b (Desc Name) Record 33
-- From source: AMENDMENT Regional Data J2735 (JPN)
Node-LLdms-80b ::=  SEQUENCE {
   lon  LongitudeDMS2,
   lat  LatitudeDMS2
   }

-- DF_REG_LaneDataAttribute_JPN (Desc Name) Record 46
-- From source: AMENDMENT Regional Data J2735 (JPN)
JPN-Reg-LaneDataAttribute ::=  SEQUENCE { ... }

-- DF_REG_MovementEvent_JPN (Desc Name) Record 49
-- From source: AMENDMENT Regional Data J2735 (JPN)
JPN-Reg-MovementEvent ::=  SEQUENCE {
   -- A set of countdown style time-to-change values
   -- all in units of 0.1 seconds and following
   -- the naming of the base DSRC standard

   startTime   TimeRemaining   OPTIONAL,
               -- When this phase 1st started
   minEndTime  MinTimetoChange,
               -- Expected shortest end time
   maxEndTime  MaxTimetoChange OPTIONAL,
               -- Expected longer end time
   likelyTime  TimeRemaining   OPTIONAL,
               -- Best predicted value based on other data             
   confidence  DSRC.TimeIntervalConfidence   OPTIONAL,
               -- Applies to above time element only
   nextTime    TimeRemaining   OPTIONAL,
   ...
   }

-- DF_REG_NodeOffsetPoint_JPN (Desc Name) Record 54
-- From source: AMENDMENT Regional Data J2735 (JPN)
JPN-Reg-NodeOffsetPoint ::=  CHOICE {
   -- Full position expressed in units of 0.01 seconds
   posA    Node-LLdms-48b,

   -- Full position expressed in multiple elements in
   -- an DD.MM.SS.sss style format
   posB    Node-LLdms-80b,

   ...
   }

-- DF_REG_Position3D_JPN (Desc Name) Record 56
-- From source: AMENDMENT Regional Data J2735 (JPN)
JPN-Reg-Position3D ::=  SEQUENCE {
   latitude     LatitudeDMS2,
   longitude    LongitudeDMS2,
   elevation    JPN-Elevation,
   ...
   }

-- DE_Second_JPN (Desc Name) Record 64
-- From source: AMENDMENT Regional Data J2735 (JPN)
Second ::= INTEGER (0..60) 
   -- BCD coding of a second of time, in 1 byte
   -- values above a combined BCD value of 60
   -- (i.e. 0110 0000) shall not be sent
   -- except that value 255 (0xFF) shall indicate an invalid value

-- DE_SecondsAngle_JPN (Desc Name) Record 65
-- From source: AMENDMENT Regional Data J2735 (JPN)
SecondsAngle ::= INTEGER (0..5999)  
   -- Unsigned units of 1/100th seconds of angle, in 2 bytes
   -- values from 6000 to 65534 shall not be sent
   -- the value 65535 (0xFFFF) shall indicate an invalid value

-- DE_SummerTime_JPN (Desc Name) Record 68
-- From source: AMENDMENT Regional Data J2735 (JPN)
SummerTime ::= ENUMERATED {
    notInSummerTime   (0),
    inSummerTime      (1)
    }
   -- Encoding as per above, in 1 bit

-- DE_TenthSecond_JPN (Desc Name) Record 69
-- From source: AMENDMENT Regional Data J2735 (JPN)
TenthSecond ::= INTEGER (0..9) 
   -- Unsigned units of 100 milliseconds, in 1 byte
   -- values from 10 to 254 shall not be sent
   -- the value 255 (0xFF) shall indicate an invalid value

-- DF_TimeMark_JPN (Desc Name) Record 70
-- From source: AMENDMENT Regional Data J2735 (JPN)
JPN-TimeMark ::=  SEQUENCE {
    year        Year,         -- BCD coding of A.D. 2 bytes
    month       Month,        -- BCD coding of Month, 1 byte
    day         Day,          -- BCD coding of Day, 1 byte
    summerTime  SummerTime,
    holiday     Holiday,
    dayofWeek   DayOfWeek,
    hour        Hour,         -- BCD coding of Hour, 1 byte
    minute      Minute,       -- BCD coding of Minute, 1 byte
    second      Second,       -- BCD coding of Second, 1 byte
    tenthSecond TenthSecond   -- units of 100 millisecond, 1 byte
}

-- DE_TimeRemaining_JPN (Desc Name) Record 71
-- From source: AMENDMENT Regional Data J2735 (JPN)
TimeRemaining ::= INTEGER (0..9001)
    -- Unsigned units of 0.1 seconds, spanning 15 minutes, in 2 bytes
    -- the value 9001 shall indicate 'forever'
    -- values from 9002 to 65534 shall not be sent
    -- the value 65535 (0xFFFF) shall indicate an invalid value

-- DE_Year_JPN (Desc Name) Record 75
-- From source: AMENDMENT Regional Data J2735 (JPN)
Year ::= INTEGER (1..65535)
   -- BCD coding of four digits of the year A.D. in 2 bytes
   -- values with nibble values between 1010 and 1111 shall not be sent
   -- except that the value 65535 (0xFFFF) shall indicate an invalid value


-- Unable to find the file: JPNstubs.txt
-- Which would be be inserted at this point if present.


 
END
-- End of the JPN module.
 
-- ^-^-^-^-^-^-^-^-^-^-^-^-^-^-^-^-^-^-^-^-^-^-^-^-^-^-^-^-
-- 
-- Begin module: NTCIP
-- 
-- ^-^-^-^-^-^-^-^-^-^-^-^-^-^-^-^-^-^-^-^-^-^-^-^-^-^-^-^-
NTCIP DEFINITIONS AUTOMATIC TAGS::= BEGIN 
 


-- ESS_EssMobileFriction (Desc Name) Record 11
-- From source: NTCIP 1204
EssMobileFriction ::= INTEGER (0..101)

-- ESS_EssPrecipRate_quantity (Desc Name) Record 12
-- From source: NTCIP 1204
EssPrecipRate ::= INTEGER (0..65535) 

-- ESS_EssPrecipSituation_code (Desc Name) Record 13
-- From source: NTCIP 1204
EssPrecipSituation ::= ENUMERATED {
   other (1), 
   unknown (2), 
   noPrecipitation (3), 
   unidentifiedSlight (4), 
   unidentifiedModerate (5), 
   unidentifiedHeavy (6), 
   snowSlight (7), 
   snowModerate (8), 
   snowHeavy (9), 
   rainSlight (10), 
   rainModerate (11), 
   rainHeavy (12), 
   frozenPrecipitationSlight (13), 
   frozenPrecipitationModerate (14), 
   frozenPrecipitationHeavy (15)
   }

-- ESS_EssPrecipYesNo_code (Desc Name) Record 14
-- From source: NTCIP 1204
EssPrecipYesNo ::= ENUMERATED {precip (1), noPrecip (2), error (3)} 

-- ESS_EssSolarRadiation_quantity (Desc Name) Record 15
-- From source: NTCIP 1204
EssSolarRadiation ::= INTEGER (0..65535) 


-- Unable to find the file: NTCIPstubs.txt
-- Which would be be inserted at this point if present.


 
END
-- End of the NTCIP module.
 
-- ^-^-^-^-^-^-^-^-^-^-^-^-^-^-^-^-^-^-^-^-^-^-^-^-^-^-^-^-
-- 
-- Begin module: ITIS
-- 
-- ^-^-^-^-^-^-^-^-^-^-^-^-^-^-^-^-^-^-^-^-^-^-^-^-^-^-^-^-
ITIS DEFINITIONS AUTOMATIC TAGS::= BEGIN 
 


-- DE_Incident Response Equipment (Desc Name) Record 18
-- From source: SAE ITIS Terms
IncidentResponseEquipment ::= ENUMERATED { 
   ground-fire-suppression          (9985),   
   heavy-ground-equipment           (9986),   
   aircraft                         (9988),   
   marine-equipment                 (9989),   
   support-equipment                (9990),   
   medical-rescue-unit              (9991),   
   other                            (9993),   -- Depreciated by fire standards, do not
                                              -- use
   ground-fire-suppression-other    (9994),   
   engine                           (9995),   
   truck-or-aerial                  (9996),   
   quint                            (9997),   -- A five-function type of fire apparatus.
                                              -- The units in the movie Backdraft were
                                              -- quints
   tanker-pumper-combination        (9998),   
   brush-truck                      (10000),  
   aircraft-rescue-firefighting     (10001),  
   heavy-ground-equipment-other     (10004),  
   dozer-or-plow                    (10005),  
   tractor                          (10006),  
   tanker-or-tender                 (10008),  
   aircraft-other                   (10024),  
   aircraft-fixed-wing-tanker       (10025),  
   helitanker                       (10026),  
   helicopter                       (10027),  
   marine-equipment-other           (10034),  
   fire-boat-with-pump              (10035),  
   boat-no-pump                     (10036),  
   support-apparatus-other          (10044),  
   breathing-apparatus-support      (10045),  
   light-and-air-unit               (10046),  
   medical-rescue-unit-other        (10054),  
   rescue-unit                      (10055),  
   urban-search-rescue-unit         (10056),  
   high-angle-rescue                (10057),  
   crash-fire-rescue                (10058),  
   bLS-unit                         (10059),  
   aLS-unit                         (10060),  
   mobile-command-post              (10075),  -- Depreciated, do not use
   chief-officer-car                (10076),  
   hAZMAT-unit                      (10077),  
   type-i-hand-crew                 (10078),  
   type-ii-hand-crew                (10079),  
   privately-owned-vehicle          (10083),  -- (Often found in volunteer fire teams)
   other-apparatus-resource         (10084),  -- (Remapped from fire code zero)
   ambulance                        (10085),  
   bomb-squad-van                   (10086),  
   combine-harvester                (10087),  
   construction-vehicle             (10088),  
   farm-tractor                     (10089),  
   grass-cutting-machines           (10090),  
   hAZMAT-containment-tow           (10091),  
   heavy-tow                        (10092),  
   light-tow                        (10094),  
   flatbed-tow                      (10114), 
   hedge-cutting-machines           (10093),  
   mobile-crane                     (10095),  
   refuse-collection-vehicle        (10096),  
   resurfacing-vehicle              (10097),  
   road-sweeper                     (10098),  
   roadside-litter-collection-crews (10099),  
   salvage-vehicle                  (10100),  
   sand-truck                       (10101),  
   snowplow                         (10102),  
   steam-roller                     (10103),  
   swat-team-van                    (10104),  
   track-laying-vehicle             (10105),  
   unknown-vehicle                  (10106),  
   white-lining-vehicle             (10107),  -- Consider using Roadwork "road marking
                                              -- operations" unless the objective is to
                                              -- refer to the specific vehicle of this
                                              -- type.  Alternative Rendering: line
                                              -- painting vehicle
   dump-truck                       (10108),  
   supervisor-vehicle               (10109),  
   snow-blower                      (10110),  
   rotary-snow-blower               (10111),  
   road-grader                      (10112),  -- Alternative term: motor grader
   steam-truck                      (10113),  -- A special truck that thaws culverts and
                                              -- storm drains
   ... -- # LOCAL_CONTENT_ITIS 
   }

-- EXT_ITIS_Codes (Desc Name) Record 19
-- From source: Adopted SAE J2540-2  (ITIS Phrases), March 2002
ITIScodes ::= INTEGER (0..65565)
-- The defined list of ITIS codes is too long to list here
-- Many smaller lists use a sub-set of these codes as defined elements
-- Also enumerated values expressed as text constant are very common,
-- and in many deployments the list codes are used as a shorthand for
-- this text.  Also the XML expressions commonly use a union of the 
-- code values and the textual expressions.  
-- Consult SAE J2540 for further details.

-- DF_ITIS-Codes_And_Text (Desc Name) Record 20
-- From source: Adopted SAE J2540-2  (ITIS Phrases), March 2002
ITIScodesAndText ::=  SEQUENCE (SIZE(1..100)) OF SEQUENCE {
  item-itis CHOICE    {
       itis ITIScodes,
       text ITIStext
       } -- # UNTAGGED
  }

-- DE_ITIS_Text (Desc Name) Record 21
-- From source: Adopted SAE J2540-2  (ITIS Phrases), March 2002
ITIStext ::= IA5String (SIZE(1..500))

-- DE_Responder Group Affected (Desc Name) Record 63
-- From source: SAE ITIS Terms
ResponderGroupAffected ::= ENUMERATED  { 
   emergency-vehicle-units           (9729),  -- Default phrase, to be used when one of
                                              -- the below does not fit better
   federal-law-enforcement-units     (9730),  
   state-police-units                (9731),  
   county-police-units               (9732),  -- Hint: also sheriff response units
   local-police-units                (9733),  
   ambulance-units                   (9734),  
   rescue-units                      (9735),  
   fire-units                        (9736),  
   hAZMAT-units                      (9737),  
   light-tow-unit                    (9738),  
   heavy-tow-unit                    (9739),  
   freeway-service-patrols           (9740),  
   transportation-response-units     (9741),  
   private-contractor-response-units (9742),  
   ... -- # LOCAL_CONTENT_ITIS 
   }
   -- These groups are used in coordinated response and staging area information
   -- (rather than typically consumer related)


-- DE_Vehicle Groups Affected (Desc Name) Record 72
-- From source: SAE ITIS Terms
VehicleGroupAffected ::= ENUMERATED  { 
   all-vehicles                               (9217),  
   bicycles                                   (9218),  
   motorcycles                                (9219),  -- to include mopeds as well
   cars                                       (9220),  -- (remapped from ERM value of
                                                       -- zero)
   light-vehicles                             (9221),  
   cars-and-light-vehicles                    (9222),  
   cars-with-trailers                         (9223),  
   cars-with-recreational-trailers            (9224),  
   vehicles-with-trailers                     (9225),  
   heavy-vehicles                             (9226),  
   trucks                                     (9227),  
   buses                                      (9228),  
   articulated-buses                          (9229),  
   school-buses                               (9230),  
   vehicles-with-semi-trailers                (9231),  
   vehicles-with-double-trailers              (9232),  -- Alternative Rendering:  western
                                                       -- doubles
   high-profile-vehicles                      (9233),  
   wide-vehicles                              (9234),  
   long-vehicles                              (9235),  
   hazardous-loads                            (9236),  
   exceptional-loads                          (9237),  
   abnormal-loads                             (9238),  
   convoys                                    (9239),  
   maintenance-vehicles                       (9240),  
   delivery-vehicles                          (9241),  
   vehicles-with-even-numbered-license-plates (9242),  
   vehicles-with-odd-numbered-license-plates  (9243),  
   vehicles-with-parking-permits              (9244),  
   vehicles-with-catalytic-converters         (9245),  
   vehicles-without-catalytic-converters      (9246),  
   gas-powered-vehicles                       (9247),  
   diesel-powered-vehicles                    (9248),  
   lPG-vehicles                               (9249),  
   military-convoys                           (9250),  
   military-vehicles                          (9251),  
   ... -- # LOCAL_CONTENT_ITIS 
   }
   -- Classification of vehicles and types of transport



-- Unable to find the file: ITISstubs.txt
-- Which would be be inserted at this point if present.


 
END
-- End of the ITIS module.
 
-- ^-^-^-^-^-^-^-^-^-^-^-^-^-^-^-^-^-^-^-^-^-^-^-^-^-^-^-^-
-- 
-- Begin module: REGION
-- 
-- ^-^-^-^-^-^-^-^-^-^-^-^-^-^-^-^-^-^-^-^-^-^-^-^-^-^-^-^-
REGION DEFINITIONS AUTOMATIC TAGS::= BEGIN 
 


-- DF_REG_AdvisorySpeed_Base (Desc Name) Record 36
-- From source: AMENDMENT Regional Data J2735 (DSRC)
Reg-AdvisorySpeed ::=  SEQUENCE { ... }

-- DF_REG_ComputedLane_Base (Desc Name) Record 37
-- From source: AMENDMENT Regional Data J2735 (DSRC)
Reg-ComputedLane ::=  SEQUENCE { ... }

-- DF_REG_ConnectionManeuverAssist_Base (Desc Name) Record 39
-- From source: AMENDMENT Regional Data J2735 (DSRC)
Reg-ConnectionManeuverAssist ::=  SEQUENCE { ... }

-- DF_REG_GenericLane_Base (Desc Name) Record 40
-- From source: AMENDMENT Regional Data J2735 (DSRC)
Reg-GenericLane ::=  SEQUENCE { ... }

-- DF_REG_Intersection_Base (Desc Name) Record 41
-- From source: AMENDMENT Regional Data J2735 (DSRC)
Reg-Intersection ::=  SEQUENCE { ... }

-- DF_REG_IntersectionState_Base (Desc Name) Record 43
-- From source: AMENDMENT Regional Data J2735 (DSRC)
Reg-IntersectionState ::=  SEQUENCE { ... }

-- DF_REG_LaneAttributes_Base (Desc Name) Record 44
-- From source: AMENDMENT Regional Data J2735 (DSRC)
Reg-LaneAttributes ::=  SEQUENCE { ... }

-- DF_REG_LaneDataAttribute_Base (Desc Name) Record 45
-- From source: AMENDMENT Regional Data J2735 (DSRC)
Reg-LaneDataAttribute ::=  SEQUENCE { ... }

-- DF_REG_MapData_Base (Desc Name) Record 47
-- From source: AMENDMENT Regional Data J2735 (DSRC)
Reg-MapData ::=  SEQUENCE { ... }

-- DF_REG_MovementEvent_Base (Desc Name) Record 50
-- From source: AMENDMENT Regional Data J2735 (DSRC)
Reg-MovementEvent ::=  SEQUENCE { ... }

-- DF_REG_MovementState_Base (Desc Name) Record 51
-- From source: AMENDMENT Regional Data J2735 (DSRC)
Reg-MovementState ::=  SEQUENCE { ... }

-- DF_REG_NodeAttribute_Base (Desc Name) Record 52
-- From source: AMENDMENT Regional Data J2735 (DSRC)
Reg-NodeAttribute ::=  SEQUENCE { ... }

-- DF_REG_NodeOffsetPoint_Base (Desc Name) Record 53
-- From source: AMENDMENT Regional Data J2735 (DSRC)
Reg-NodeOffsetPoint ::=  SEQUENCE { ... }

-- DF_REG_Position3D_Base (Desc Name) Record 55
-- From source: AMENDMENT Regional Data J2735 (DSRC)
Reg-Position3D ::=  SEQUENCE { ... }

-- DF_REG_RestrictionUserType_Base (Desc Name) Record 59
-- From source: AMENDMENT Regional Data J2735 (DSRC)
Reg-RestrictionUserType ::=  SEQUENCE { ... }

-- DF_REG_RoadSegment_Base (Desc Name) Record 60
-- From source: AMENDMENT Regional Data J2735 (DSRC)
Reg-RoadSegment ::=  SEQUENCE { ... }

-- DF_REG_SignalControlZone_Base (Desc Name) Record 61
-- From source: AMENDMENT Regional Data J2735 (DSRC)
Reg-SignalControlZone ::=  SEQUENCE { ... }

-- DF_REG_SPAT_Base (Desc Name) Record 62
-- From source: AMENDMENT Regional Data J2735 (DSRC)
Reg-SPAT ::=  SEQUENCE { ... }


-- Unable to find the file: REGIONstubs.txt
-- Which would be be inserted at this point if present.


 
END
-- End of the REGION module.
 
 
-- No entries were found with unknown module assignments.
 
 


-- Unable to find the file: ASNstubs.txt
-- Which would be be inserted at this point if present.



-- Authoritative copies of the official ASN source code specification contained
-- in the SAE J2735 DSRC Message Set standard are freely available from the SAE.
-- End of file output at 11/19/2014 00:00:00 AM
